WINDOWS-NT-PERFORMANCE DEFINITIONS ::= BEGIN
    IMPORTS
        enterprises
            FROM RFC1155-SMI
        OBJECT-TYPE
            FROM RFC-1212
        DisplayString
            FROM RFC1213-MIB;

    microsoft   OBJECT IDENTIFIER ::= { enterprises 311 }
    software    OBJECT IDENTIFIER ::= { microsoft 1 }
    systems     OBJECT IDENTIFIER ::= { software 1 }
    os          OBJECT IDENTIFIER ::= { systems 3 }
    winnt       OBJECT IDENTIFIER ::= { os 1 }
    performance OBJECT IDENTIFIER ::= { winnt 1 }



    -- memory MIB

    memory OBJECT IDENTIFIER ::= { performance 1 }

    memoryAvailableBytes OBJECT-TYPE
        SYNTAX INTEGER
        ACCESS read-only
        STATUS mandatory
        DESCRIPTION
            "Available Bytes displays the size of the virtual memory currently on the Zeroed, Free, and Standby lists.  Zeroed and Free memory is ready for use, with Zeroed memory cleared to zeros.  Standby memory is memory removed from a process's Working Set but still available.  Notice that this is an instantaneous count, not an average over the time interval."
        ::= { memory 1 }

    memoryCommittedBytes OBJECT-TYPE
        SYNTAX INTEGER
        ACCESS read-only
        STATUS mandatory
        DESCRIPTION
            "Committed Bytes displays the size of virtual memory (in bytes) that has been Committed (as opposed to simply reserved).  Committed memory must have backing (i.e., disk) storage available, or must be assured never to need disk storage (because main memory is large enough to hold it.)  Notice that this is an instantaneous count, not an average over the time interval."
        ::= { memory 2 }

    memoryCommitLimit OBJECT-TYPE
        SYNTAX INTEGER
        ACCESS read-only
        STATUS mandatory
        DESCRIPTION
            "Commit Limit is the size (in bytes) of virtual memory that can be committed without having to extend the paging file(s).  If the paging file(s) can be extended, this is a soft limit."
        ::= { memory 3 }

    memoryPageFaultsPerSec OBJECT-TYPE
        SYNTAX Counter
        ACCESS read-only
        STATUS mandatory
        DESCRIPTION
            "Page Faults/sec is a count of the Page Faults in the processor.  A page fault occurs when a process refers to a virtual memory page that is not in its Working Set in main memory.  A Page Fault will not cause the page to be fetched from disk if that page is on the standby list, and hence already in main memory, or if it is in use by another process with whom the page is shared."
        ::= { memory 4 }

    memoryWriteCopiesPerSec OBJECT-TYPE
        SYNTAX Counter
        ACCESS read-only
        STATUS mandatory
        DESCRIPTION
            "Write Copies/sec is the number of page faults that have been satisfied by making a copy of a page when an attempt to write to the page is made.  This is an economical way of sharing data since the copy of the page is only made on an attempt to write to the page; otherwise, the page is shared."
        ::= { memory 5 }

    memoryTransitionFaultsPerSec OBJECT-TYPE
        SYNTAX Counter
        ACCESS read-only
        STATUS mandatory
        DESCRIPTION
            "Transition Faults/sec is the number of page faults resolved by recovering pages that were in transition, i.e., being written to disk at the time of the page fault.  The pages were recovered without additional disk activity."
        ::= { memory 6 }

    memoryCacheFaultsPerSec OBJECT-TYPE
        SYNTAX Counter
        ACCESS read-only
        STATUS mandatory
        DESCRIPTION
            "Cache Faults occur whenever the Cache manager does not find a file's page in the immediate Cache and must ask the memory manager to locate the page elsewhere in memory or on the disk so that it can be loaded into the immediate Cache."
        ::= { memory 7 }

    memoryDemandZeroFaultsPerSec OBJECT-TYPE
        SYNTAX Counter
        ACCESS read-only
        STATUS mandatory
        DESCRIPTION
            "Demand Zero Faults are the number of page faults for pages that must be filled with zeros before the fault is satisfied.  If the Zeroed list is not empty, the fault can be resolved by removing a page from the Zeroed list."
        ::= { memory 8 }

    memoryPagesPerSec OBJECT-TYPE
        SYNTAX Counter
        ACCESS read-only
        STATUS mandatory
        DESCRIPTION
            "Pages/sec is the number of pages read from the disk or written to the disk to resolve memory references to pages that were not in memory at the time of the reference.  This is the sum of Pages Input/sec and Pages Output/sec.  This counter includes paging traffic on behalf of the system Cache to access file data for applications.  This value also includes the pages to/from non-cached mapped memory files.  This is the primary counter to observe if you are concerned about excessive memory pressure (that is, thrashing), and the excessive paging that may result."
        ::= { memory 9 }

    memoryPagesInputPerSec OBJECT-TYPE
        SYNTAX Counter
        ACCESS read-only
        STATUS mandatory
        DESCRIPTION
            "Pages Input/sec is the number of pages read from the disk to resolve memory references to pages that were not in memory at the time of the reference.  This counter includes paging traffic on behalf of the system Cache to access file data for applications.  This is an important counter to observe if you are concerned about excessive memory pressure (that is, thrashing), and the excessive paging that may result."
        ::= { memory 10 }

    memoryPageReadsPerSec OBJECT-TYPE
        SYNTAX Counter
        ACCESS read-only
        STATUS mandatory
        DESCRIPTION
            "Page Reads/sec is the number of times the disk was read to retrieve pages of virtual memory necessary to resolve page faults.  Multiple pages can be read during a disk read operation."
        ::= { memory 11 }

    memoryPagesOutputPerSec OBJECT-TYPE
        SYNTAX Counter
        ACCESS read-only
        STATUS mandatory
        DESCRIPTION
            "Pages Output/sec is a count of the number of pages that are written to disk because the pages have been modified in main memory."
        ::= { memory 12 }

    memoryPageWritesPerSec OBJECT-TYPE
        SYNTAX Counter
        ACCESS read-only
        STATUS mandatory
        DESCRIPTION
            "Page Writes/sec is a count of the number of times pages have been written to the disk because they were changed since last retrieved.  Each such write operation may transfer a number of pages."
        ::= { memory 13 }

    memoryPoolPagedBytes OBJECT-TYPE
        SYNTAX INTEGER
        ACCESS read-only
        STATUS mandatory
        DESCRIPTION
            "Pool Paged Bytes is the number of bytes in the Paged Pool, a system memory area where space is acquired by operating system components as they accomplish their appointed tasks.  Paged Pool pages can be paged out to the paging file when not accessed by the system for sustained periods of time."
        ::= { memory 14 }

    memoryPoolNonpagedBytes OBJECT-TYPE
        SYNTAX INTEGER
        ACCESS read-only
        STATUS mandatory
        DESCRIPTION
            "Pool Nonpaged Bytes is the number of bytes in the Nonpaged Pool, a system memory area where space is acquired by operating system components as they accomplish their appointed tasks.  Nonpaged Pool pages cannot be paged out to the paging file, but instead remain in main memory as long as they are allocated."
        ::= { memory 15 }

    memoryPoolPagedAllocs OBJECT-TYPE
        SYNTAX INTEGER
        ACCESS read-only
        STATUS mandatory
        DESCRIPTION
            "Pool Paged Allocs is the number of calls to allocate space in the system Paged Pool.  Paged Pool is a system memory area where space is acquired by operating system components as they accomplish their appointed tasks.  Paged Pool pages can be paged out to the paging file when not accessed by the system for sustained periods of time."
        ::= { memory 16 }

    memoryPoolNonpagedAllocs OBJECT-TYPE
        SYNTAX INTEGER
        ACCESS read-only
        STATUS mandatory
        DESCRIPTION
            "Pool Nonpaged Allocs is the number of calls to allocate space in the system Nonpaged Pool.  Nonpaged Pool is a system memory area where space is acquired by operating system components as they accomplish their appointed tasks.  Nonpaged Pool pages cannot be paged out to the paging file, but instead remain in main memory as long as they are allocated."
        ::= { memory 17 }

    memoryFreeSystemPageTableEntries OBJECT-TYPE
        SYNTAX INTEGER
        ACCESS read-only
        STATUS mandatory
        DESCRIPTION
            "The number of Page Table Entries not currently in use by the system."
        ::= { memory 18 }

    memoryCacheBytes OBJECT-TYPE
        SYNTAX INTEGER
        ACCESS read-only
        STATUS mandatory
        DESCRIPTION
            "Cache Bytes measures the number of bytes currently in use by the system Cache.  The system Cache is used to buffer data retrieved from disk or LAN.  The system Cache uses memory not in use by active processes in the computer."
        ::= { memory 19 }

    memoryCacheBytesPeak OBJECT-TYPE
        SYNTAX INTEGER
        ACCESS read-only
        STATUS mandatory
        DESCRIPTION
            "Cache Bytes Peak measures the maximum number of bytes used by the system Cache.  The system Cache is used to buffer data retrieved from disk or LAN.  The system Cache uses memory not in use by active processes in the computer."
        ::= { memory 20 }

    memoryPoolPagedResidentBytes OBJECT-TYPE
        SYNTAX INTEGER
        ACCESS read-only
        STATUS mandatory
        DESCRIPTION
            "Pool Paged Resident Bytes is the size of paged Pool resident in core memory.  This is the actual cost of the paged Pool allocation, since this is actively in use and using real physical memory."
        ::= { memory 21 }

    memorySystemCodeTotalBytes OBJECT-TYPE
        SYNTAX INTEGER
        ACCESS read-only
        STATUS mandatory
        DESCRIPTION
            "System Code Total Bytes is the number of bytes of pagable pages in ntoskrnl.exe, hal.dll, and the boot drivers and file systems loaded by ntldr/osloader."
        ::= { memory 22 }

    memorySystemCodeResidentBytes OBJECT-TYPE
        SYNTAX INTEGER
        ACCESS read-only
        STATUS mandatory
        DESCRIPTION
            "System Code Resident Bytes is the number of bytes of System Code Total Bytes currently resident in core memory.  This is the code working set of the pagable executive.  In addition to this, there is another ~300k bytes of non-paged kernel code."
        ::= { memory 23 }

    memorySystemDriverTotalBytes OBJECT-TYPE
        SYNTAX INTEGER
        ACCESS read-only
        STATUS mandatory
        DESCRIPTION
            "System Driver Total Bytes is the number of bytes of pagable pages in all other loaded device drivers."
        ::= { memory 24 }

    memorySystemDriverResidentBytes OBJECT-TYPE
        SYNTAX INTEGER
        ACCESS read-only
        STATUS mandatory
        DESCRIPTION
            "System Driver Resident Bytes is the number of bytes of System Driver Total Bytes currently resident in core memory.  This number is the code working set of the pagable drivers.  In addition to this, there is another ~700k bytes of non-paged driver code."
        ::= { memory 25 }

    memorySystemCacheResidentBytes OBJECT-TYPE
        SYNTAX INTEGER
        ACCESS read-only
        STATUS mandatory
        DESCRIPTION
            "System Cache Resident Bytes is the number of bytes currently resident in the global disk cache."
        ::= { memory 26 }

    memoryPercentCommittedBytesInUse OBJECT-TYPE
        SYNTAX INTEGER
        ACCESS read-only
        STATUS mandatory
        DESCRIPTION
            "% Committed Bytes In Use is the ratio of the Commited Bytes to the Commit Limit. This represents the amount of available virtual memory in use. Note that the Commit Limit may change if the paging file is extended. This is an instantaneous value, not an average."
        ::= { memory 27 }

    -- processor MIB

    cpuprocessorTable OBJECT-TYPE
        SYNTAX SEQUENCE OF cpuprocessorEntry
        ACCESS not-accessible
        STATUS mandatory
        DESCRIPTION
            "A table containing performance information for instances of 'processor' objects."
        ::= { performance 2 }

    cpuprocessorEntry OBJECT-TYPE
        SYNTAX cpuprocessorEntry
        ACCESS not-accessible
        STATUS mandatory
        DESCRIPTION
            "Performance information for one particular instance of 'processor' object."
        INDEX { cpuprocessorIndex }
        ::= { cpuprocessorTable 1 }

    cpuprocessorEntry ::=
        SEQUENCE {
            cpuprocessorIndex INTEGER,
            cpuprocessorInstance DisplayString,
            cpuPercentProcessorTime INTEGER,
            cpuPercentUserTime INTEGER,
            cpuPercentPrivilegedTime INTEGER,
            cpuInterruptsPerSec Counter,
            cpuPercentDPCTime INTEGER,
            cpuPercentInterruptTime INTEGER,
            cpuDPCsQueuedPerSec Counter,
            cpuDPCRate INTEGER,
            cpuDPCBypassesPerSec Counter,
            cpuAPCBypassesPerSec Counter
        }

    cpuprocessorIndex OBJECT-TYPE
        SYNTAX INTEGER
        ACCESS read-only
        STATUS mandatory
        DESCRIPTION
            "Index."
        ::= { cpuprocessorEntry 1 }

    cpuprocessorInstance OBJECT-TYPE
        SYNTAX DisplayString
        ACCESS read-only
        STATUS mandatory
        DESCRIPTION
            "Instance name."
        ::= { cpuprocessorEntry 2 }

    cpuPercentProcessorTime OBJECT-TYPE
        SYNTAX INTEGER
        ACCESS read-only
        STATUS mandatory
        DESCRIPTION
            "Processor Time is expressed as a percentage of the elapsed time that a processor is busy executing a non-Idle thread.  It can be viewed as the fraction of the time spent doing useful work.  Each processor is assigned an Idle thread in the Idle process which consumes those unproductive processor cycles not used by any other threads."
        ::= { cpuprocessorEntry 3 }

    cpuPercentUserTime OBJECT-TYPE
        SYNTAX INTEGER
        ACCESS read-only
        STATUS mandatory
        DESCRIPTION
            "User Time is the percentage of processor time spent in User Mode in non-Idle threads.  All application code and subsystem code execute in User Mode.  The graphics engine, graphics device drivers, printer device drivers, and the window manager also execute in User Mode.  Code executing in User Mode cannot damage the integrity of the Windows NT Executive, Kernel, and device drivers.  Unlike some early operating systems, Windows NT uses process boundaries for subsystem protection in addition to the traditional protection of User and Privileged modes.  These subsystem processes provide additional protection.  Therefore, some work done by Windows NT on behalf of your application may appear in other subsystem processes in addition to the Privileged Time in your process."
        ::= { cpuprocessorEntry 4 }

    cpuPercentPrivilegedTime OBJECT-TYPE
        SYNTAX INTEGER
        ACCESS read-only
        STATUS mandatory
        DESCRIPTION
            "Privileged Time is the percentage of processor time spent in Privileged Mode in non-Idle threads.  The Windows NT service layer, the Executive routines, and the Windows NT Kernel execute in Privileged Mode.  Device drivers for most devices other than graphics adapters and printers also execute in Privileged Mode.  Unlike some early operating systems, Windows NT uses process boundaries for subsystem protection in addition to the traditional protection of User and Privileged modes.  These subsystem processes provide additional protection.  Therefore, some work done by Windows NT on behalf of your application may appear in other subsystem processes in addition to the Privileged Time in your process."
        ::= { cpuprocessorEntry 5 }

    cpuInterruptsPerSec OBJECT-TYPE
        SYNTAX Counter
        ACCESS read-only
        STATUS mandatory
        DESCRIPTION
            "Interrupts/sec is the number of device interrupts the processor is experiencing.  A device interrupts the processor when it has completed a task or when it otherwise requires attention.  Normal thread execution is suspended during interrupts.  An interrupt may cause the processor to switch to another, higher priority thread.  Clock interrupts are frequent and periodic and create a background of interrupt activity."
        ::= { cpuprocessorEntry 6 }

    cpuPercentDPCTime OBJECT-TYPE
        SYNTAX INTEGER
        ACCESS read-only
        STATUS mandatory
        DESCRIPTION
            "% DPC Time is the percentage of elapsed time that the Processor spent in Deferred Procedure Calls.  When a hardware device interrupts the Processor, the Interrupt Handler may elect to execute the majority of its work in a DPC.  DPC's run at lower priority than Interrupts, and so permit Interrupts to occur while DPC's being execute.  Deferred Procedure Calls are executed in Privileged Mode, so this is a component of Processor: % Privileged Time.  This counter can help determine the source of excessive time being spent in Privileged Mode."
        ::= { cpuprocessorEntry 7 }

    cpuPercentInterruptTime OBJECT-TYPE
        SYNTAX INTEGER
        ACCESS read-only
        STATUS mandatory
        DESCRIPTION
            "% Interrupt Time is the percentage of elapsed time that the Processor spent handling hardware Interrupts.  When a hardware device interrupts the Processor, the Interrupt Handler will execute to handle the condition, usually by signaling I/O completion and possibly issuing another pending I/O request.  Some of this work may be done in a Deferred Procedure Call (see % DPC Time.)  However, time spent in DPC's is not counted as time in Interrupts.  Interrupts are executed in Privileged Mode, so this is a component of Processor: % Privileged Time.  This counter can help determine the source of excessive time being spent in Privileged Mode."
        ::= { cpuprocessorEntry 8 }

    cpuDPCsQueuedPerSec OBJECT-TYPE
        SYNTAX Counter
        ACCESS read-only
        STATUS mandatory
        DESCRIPTION
            "DPCs Queued/sec is the rate DPC objects are queued to this processor's DPC queue."
        ::= { cpuprocessorEntry 9 }

    cpuDPCRate OBJECT-TYPE
        SYNTAX INTEGER
        ACCESS read-only
        STATUS mandatory
        DESCRIPTION
            "DPC Rate is the average rate DPC objects are queued to this processor's DPC queue per clock tick."
        ::= { cpuprocessorEntry 10 }

    cpuDPCBypassesPerSec OBJECT-TYPE
        SYNTAX Counter
        ACCESS read-only
        STATUS mandatory
        DESCRIPTION
            "DPC Bypasses/sec is the rate Dispatch interrupts were short-circuited."
        ::= { cpuprocessorEntry 11 }

    cpuAPCBypassesPerSec OBJECT-TYPE
        SYNTAX Counter
        ACCESS read-only
        STATUS mandatory
        DESCRIPTION
            "APC Bypasses/sec is the rate kernel APC interrupts were short-circuited."
        ::= { cpuprocessorEntry 12 }

    -- network Interface MIB

    netnetwork-InterfaceTable OBJECT-TYPE
        SYNTAX SEQUENCE OF netnetwork-InterfaceEntry
        ACCESS not-accessible
        STATUS mandatory
        DESCRIPTION
            "A table containing performance information for instances of 'network-Interface' objects."
        ::= { performance 3 }

    netnetwork-InterfaceEntry OBJECT-TYPE
        SYNTAX netnetwork-InterfaceEntry
        ACCESS not-accessible
        STATUS mandatory
        DESCRIPTION
            "Performance information for one particular instance of 'network-Interface' object."
        INDEX { netnetwork-InterfaceIndex }
        ::= { netnetwork-InterfaceTable 1 }

    netnetwork-InterfaceEntry ::=
        SEQUENCE {
            netnetwork-InterfaceIndex INTEGER,
            netnetwork-InterfaceInstance DisplayString,
            netBytesTotalPerSec Counter,
            netPacketsPerSec Counter,
            netPacketsReceivedPerSec Counter,
            netPacketsSentPerSec Counter,
            netCurrentBandwidth INTEGER,
            netBytesReceivedPerSec Counter,
            netPacketsReceivedUnicastPerSec Counter,
            netPacketsReceivedNon-UnicastPerSec Counter,
            netPacketsReceivedDiscarded INTEGER,
            netPacketsReceivedErrors INTEGER,
            netPacketsReceivedUnknown INTEGER,
            netBytesSentPerSec Counter,
            netPacketsSentUnicastPerSec Counter,
            netPacketsSentNon-UnicastPerSec Counter,
            netPacketsOutboundDiscarded INTEGER,
            netPacketsOutboundErrors INTEGER,
            netOutputQueueLength INTEGER
        }

    netnetwork-InterfaceIndex OBJECT-TYPE
        SYNTAX INTEGER
        ACCESS read-only
        STATUS mandatory
        DESCRIPTION
            "Index."
        ::= { netnetwork-InterfaceEntry 1 }

    netnetwork-InterfaceInstance OBJECT-TYPE
        SYNTAX DisplayString
        ACCESS read-only
        STATUS mandatory
        DESCRIPTION
            "Instance name."
        ::= { netnetwork-InterfaceEntry 2 }

    netBytesTotalPerSec OBJECT-TYPE
        SYNTAX Counter
        ACCESS read-only
        STATUS mandatory
        DESCRIPTION
            "Bytes Total/sec is the rate that bytes are sent and received on the interface, including framing characters."
        ::= { netnetwork-InterfaceEntry 3 }

    netPacketsPerSec OBJECT-TYPE
        SYNTAX Counter
        ACCESS read-only
        STATUS mandatory
        DESCRIPTION
            "Packets/sec is the rate that packets are sent and received on the network interface."
        ::= { netnetwork-InterfaceEntry 4 }

    netPacketsReceivedPerSec OBJECT-TYPE
        SYNTAX Counter
        ACCESS read-only
        STATUS mandatory
        DESCRIPTION
            "Packets Received/sec is the rate that packets are received on the network interface."
        ::= { netnetwork-InterfaceEntry 5 }

    netPacketsSentPerSec OBJECT-TYPE
        SYNTAX Counter
        ACCESS read-only
        STATUS mandatory
        DESCRIPTION
            "Packets Sent/sec is the rate that packets are sent on the network interface."
        ::= { netnetwork-InterfaceEntry 6 }

    netCurrentBandwidth OBJECT-TYPE
        SYNTAX INTEGER
        ACCESS read-only
        STATUS mandatory
        DESCRIPTION
            "Current Bandwidth is an estimate of the interface's current bandwidth in bits per second (bps). For interfaces that do not vary in bandwidth or for those where no accurate estimation can be made, this value is the nominal bandwidth."
        ::= { netnetwork-InterfaceEntry 7 }

    netBytesReceivedPerSec OBJECT-TYPE
        SYNTAX Counter
        ACCESS read-only
        STATUS mandatory
        DESCRIPTION
            "Bytes Received/sec is the rate that bytes are received on the interface, including framing characters."
        ::= { netnetwork-InterfaceEntry 8 }

    netPacketsReceivedUnicastPerSec OBJECT-TYPE
        SYNTAX Counter
        ACCESS read-only
        STATUS mandatory
        DESCRIPTION
            "Packets Received Unicast/sec is the rate that (subnet) unicast packets are delivered to a higher-layer protocol."
        ::= { netnetwork-InterfaceEntry 9 }

    netPacketsReceivedNon-UnicastPerSec OBJECT-TYPE
        SYNTAX Counter
        ACCESS read-only
        STATUS mandatory
        DESCRIPTION
            "Packets Received Non-Unicast/sec is the rate that non-unicast (i.e., subnet broadcast or subnet multicast) packets are delivered to a higher-layer protocol."
        ::= { netnetwork-InterfaceEntry 10 }

    netPacketsReceivedDiscarded OBJECT-TYPE
        SYNTAX INTEGER
        ACCESS read-only
        STATUS mandatory
        DESCRIPTION
            "Packets Received Discarded is the number of inbound packets that were chosen to be discarded even though no errors had been detected to prevent their being deliverable to a higher-layer protocol. One possible reason for discarding such a packet could be to free up buffer space."
        ::= { netnetwork-InterfaceEntry 11 }

    netPacketsReceivedErrors OBJECT-TYPE
        SYNTAX INTEGER
        ACCESS read-only
        STATUS mandatory
        DESCRIPTION
            "Packets Received Errors is the number of inbound packets that contained errors preventing them from being deliverable to a higher-layer protocol."
        ::= { netnetwork-InterfaceEntry 12 }

    netPacketsReceivedUnknown OBJECT-TYPE
        SYNTAX INTEGER
        ACCESS read-only
        STATUS mandatory
        DESCRIPTION
            "Packets Received Unknown is the number of packets received via the interface that were discarded because of an unknown or unsupported protocol."
        ::= { netnetwork-InterfaceEntry 13 }

    netBytesSentPerSec OBJECT-TYPE
        SYNTAX Counter
        ACCESS read-only
        STATUS mandatory
        DESCRIPTION
            "Bytes Sent/sec is the rate that bytes are sent on the interface, including framing characters."
        ::= { netnetwork-InterfaceEntry 14 }

    netPacketsSentUnicastPerSec OBJECT-TYPE
        SYNTAX Counter
        ACCESS read-only
        STATUS mandatory
        DESCRIPTION
            "Packets Sent Unicast/sec is the rate that packets are requested to be transmitted to subnet-unicast addresses by higher-level protocols.  The rate includes the packets that were discarded or not sent."
        ::= { netnetwork-InterfaceEntry 15 }

    netPacketsSentNon-UnicastPerSec OBJECT-TYPE
        SYNTAX Counter
        ACCESS read-only
        STATUS mandatory
        DESCRIPTION
            "Packets Sent Non-Unicast/sec is the rate that packets are requested to be transmitted to non-unicast (i.e., subnet broadcast or subnet multicast) addresses by higher-level protocols.  The rate includes the packets that were discarded or not sent."
        ::= { netnetwork-InterfaceEntry 16 }

    netPacketsOutboundDiscarded OBJECT-TYPE
        SYNTAX INTEGER
        ACCESS read-only
        STATUS mandatory
        DESCRIPTION
            "Packets Outbound Discarded is the number of outbound packets that were chosen to be discarded even though no errors had been detected to prevent their being transmitted.  One possible reason for discarding such a packet could be to free up buffer space."
        ::= { netnetwork-InterfaceEntry 17 }

    netPacketsOutboundErrors OBJECT-TYPE
        SYNTAX INTEGER
        ACCESS read-only
        STATUS mandatory
        DESCRIPTION
            "Packets Outbound Errors is the number of outbound packets that could not be transmitted because of errors."
        ::= { netnetwork-InterfaceEntry 18 }

    netOutputQueueLength OBJECT-TYPE
        SYNTAX INTEGER
        ACCESS read-only
        STATUS mandatory
        DESCRIPTION
            "Output Queue Length is the length of the output packet queue (in packets.)  If this is longer than 2, delays are being experienced and the bottleneck should be found and eliminated if possible.  Since the requests are queued by NDIS in this implementations, this will always be 0."
        ::= { netnetwork-InterfaceEntry 19 }

    -- physicalDisk MIB

    pdiskphysicalDiskTable OBJECT-TYPE
        SYNTAX SEQUENCE OF pdiskphysicalDiskEntry
        ACCESS not-accessible
        STATUS mandatory
        DESCRIPTION
            "A table containing performance information for instances of 'physicalDisk' objects."
        ::= { performance 4 }

    pdiskphysicalDiskEntry OBJECT-TYPE
        SYNTAX pdiskphysicalDiskEntry
        ACCESS not-accessible
        STATUS mandatory
        DESCRIPTION
            "Performance information for one particular instance of 'physicalDisk' object."
        INDEX { pdiskphysicalDiskIndex }
        ::= { pdiskphysicalDiskTable 1 }

    pdiskphysicalDiskEntry ::=
        SEQUENCE {
            pdiskphysicalDiskIndex INTEGER,
            pdiskphysicalDiskInstance DisplayString,
            pdiskCurrentDiskQueueLength INTEGER,
            pdiskPercentDiskTime TimeTicks,
            pdiskAvgDiskQueueLength INTEGER,
            pdiskPercentDiskReadTime TimeTicks,
            pdiskAvgDiskReadQueueLength INTEGER,
            pdiskPercentDiskWriteTime TimeTicks,
            pdiskAvgDiskWriteQueueLength INTEGER,
            pdiskAvgDiskSecPerTransfer TimeTicks,
            pdiskAvgDiskSecPerRead TimeTicks,
            pdiskAvgDiskSecPerWrite TimeTicks,
            pdiskDiskTransfersPerSec Counter,
            pdiskDiskReadsPerSec Counter,
            pdiskDiskWritesPerSec Counter,
            pdiskDiskBytesPerSec INTEGER,
            pdiskDiskReadBytesPerSec INTEGER,
            pdiskDiskWriteBytesPerSec INTEGER
        }

    pdiskphysicalDiskIndex OBJECT-TYPE
        SYNTAX INTEGER
        ACCESS read-only
        STATUS mandatory
        DESCRIPTION
            "Index."
        ::= { pdiskphysicalDiskEntry 1 }

    pdiskphysicalDiskInstance OBJECT-TYPE
        SYNTAX DisplayString
        ACCESS read-only
        STATUS mandatory
        DESCRIPTION
            "Instance name."
        ::= { pdiskphysicalDiskEntry 2 }

    pdiskCurrentDiskQueueLength OBJECT-TYPE
        SYNTAX INTEGER
        ACCESS read-only
        STATUS mandatory
        DESCRIPTION
            "Current Disk Queue Length is the number of requests outstanding on the disk at the time the performance data is collected.  It includes requests in service at the time of the snapshot.  This is an instantaneous length, not an average over the time interval.  Multi-spindle disk devices can have multiple requests active at one time, but other concurrent requests are awaiting service.  This counter may reflect a transitory high or low queue length, but if there is a sustained load on the disk drive, it is likely that this will be consistently high.  Requests are experiencing delays proportional to the length of this queue minus the number of spindles on the disks.  This difference should average less than 2 for good performance."
        ::= { pdiskphysicalDiskEntry 3 }

    pdiskPercentDiskTime OBJECT-TYPE
        SYNTAX TimeTicks
        ACCESS read-only
        STATUS mandatory
        DESCRIPTION
            "Disk Time is the percentage of elapsed time that the selected disk drive is busy servicing read or write requests."
        ::= { pdiskphysicalDiskEntry 4 }

    pdiskAvgDiskQueueLength OBJECT-TYPE
        SYNTAX INTEGER
        ACCESS read-only
        STATUS mandatory
        DESCRIPTION
            "Avg. Disk Queue Length is the average number of both read and write requests that were queued for the selected disk during the sample interval."
        ::= { pdiskphysicalDiskEntry 5 }

    pdiskPercentDiskReadTime OBJECT-TYPE
        SYNTAX TimeTicks
        ACCESS read-only
        STATUS mandatory
        DESCRIPTION
            "Disk Read Time is the percentage of elapsed time that the selected disk drive is busy servicing read requests."
        ::= { pdiskphysicalDiskEntry 6 }

    pdiskAvgDiskReadQueueLength OBJECT-TYPE
        SYNTAX INTEGER
        ACCESS read-only
        STATUS mandatory
        DESCRIPTION
            "Avg. Disk Read Queue Length is the average number of read requests that were queued for the selected disk during the sample interval."
        ::= { pdiskphysicalDiskEntry 7 }

    pdiskPercentDiskWriteTime OBJECT-TYPE
        SYNTAX TimeTicks
        ACCESS read-only
        STATUS mandatory
        DESCRIPTION
            "Disk Write Time is the percentage of elapsed time that the selected disk drive is busy servicing write requests."
        ::= { pdiskphysicalDiskEntry 8 }

    pdiskAvgDiskWriteQueueLength OBJECT-TYPE
        SYNTAX INTEGER
        ACCESS read-only
        STATUS mandatory
        DESCRIPTION
            "Avg. Disk Write Queue Length is the average number of write requests that were queued for the selected disk during the sample interval."
        ::= { pdiskphysicalDiskEntry 9 }

    pdiskAvgDiskSecPerTransfer OBJECT-TYPE
        SYNTAX TimeTicks
        ACCESS read-only
        STATUS mandatory
        DESCRIPTION
            "Avg. Disk sec/Transfer is the time in seconds of the average disk transfer."
        ::= { pdiskphysicalDiskEntry 10 }

    pdiskAvgDiskSecPerRead OBJECT-TYPE
        SYNTAX TimeTicks
        ACCESS read-only
        STATUS mandatory
        DESCRIPTION
            "Avg. Disk sec/Read is the average time in seconds of a read of data from the disk."
        ::= { pdiskphysicalDiskEntry 11 }

    pdiskAvgDiskSecPerWrite OBJECT-TYPE
        SYNTAX TimeTicks
        ACCESS read-only
        STATUS mandatory
        DESCRIPTION
            "Avg. Disk sec/Write is the average time in seconds of a write of data to the disk."
        ::= { pdiskphysicalDiskEntry 12 }

    pdiskDiskTransfersPerSec OBJECT-TYPE
        SYNTAX Counter
        ACCESS read-only
        STATUS mandatory
        DESCRIPTION
            "Disk Transfers/sec is the rate of read and write operations on the disk."
        ::= { pdiskphysicalDiskEntry 13 }

    pdiskDiskReadsPerSec OBJECT-TYPE
        SYNTAX Counter
        ACCESS read-only
        STATUS mandatory
        DESCRIPTION
            "Disk Reads/sec is the rate of read operations on the disk."
        ::= { pdiskphysicalDiskEntry 14 }

    pdiskDiskWritesPerSec OBJECT-TYPE
        SYNTAX Counter
        ACCESS read-only
        STATUS mandatory
        DESCRIPTION
            "Disk Writes/sec is the rate of write operations on the disk."
        ::= { pdiskphysicalDiskEntry 15 }

    pdiskDiskBytesPerSec OBJECT-TYPE
        SYNTAX INTEGER
        ACCESS read-only
        STATUS mandatory
        DESCRIPTION
            "Disk Bytes/sec is the rate bytes are transferred to or from the disk during write or read operations."
        ::= { pdiskphysicalDiskEntry 16 }

    pdiskDiskReadBytesPerSec OBJECT-TYPE
        SYNTAX INTEGER
        ACCESS read-only
        STATUS mandatory
        DESCRIPTION
            "Disk Read Bytes/sec is the rate bytes are transferred from the disk during read operations."
        ::= { pdiskphysicalDiskEntry 17 }

    pdiskDiskWriteBytesPerSec OBJECT-TYPE
        SYNTAX INTEGER
        ACCESS read-only
        STATUS mandatory
        DESCRIPTION
            "Disk Write Bytes is rate bytes are transferred to the disk during write operations."
        ::= { pdiskphysicalDiskEntry 18 }

    -- logicalDisk MIB

    ldisklogicalDiskTable OBJECT-TYPE
        SYNTAX SEQUENCE OF ldisklogicalDiskEntry
        ACCESS not-accessible
        STATUS mandatory
        DESCRIPTION
            "A table containing performance information for instances of 'logicalDisk' objects."
        ::= { performance 5 }

    ldisklogicalDiskEntry OBJECT-TYPE
        SYNTAX ldisklogicalDiskEntry
        ACCESS not-accessible
        STATUS mandatory
        DESCRIPTION
            "Performance information for one particular instance of 'logicalDisk' object."
        INDEX { ldisklogicalDiskIndex }
        ::= { ldisklogicalDiskTable 1 }

    ldisklogicalDiskEntry ::=
        SEQUENCE {
            ldisklogicalDiskIndex INTEGER,
            ldisklogicalDiskInstance DisplayString,
            ldiskPercentFreeSpace INTEGER,
            ldiskFreeMegabytes INTEGER,
            ldiskCurrentDiskQueueLength INTEGER,
            ldiskPercentDiskTime TimeTicks,
            ldiskAvgDiskQueueLength INTEGER,
            ldiskPercentDiskReadTime TimeTicks,
            ldiskAvgDiskReadQueueLength INTEGER,
            ldiskPercentDiskWriteTime TimeTicks,
            ldiskAvgDiskWriteQueueLength INTEGER,
            ldiskAvgDiskSecPerTransfer TimeTicks,
            ldiskAvgDiskSecPerRead TimeTicks,
            ldiskAvgDiskSecPerWrite TimeTicks,
            ldiskDiskTransfersPerSec Counter,
            ldiskDiskReadsPerSec Counter,
            ldiskDiskWritesPerSec Counter,
            ldiskDiskBytesPerSec INTEGER,
            ldiskDiskReadBytesPerSec INTEGER,
            ldiskDiskWriteBytesPerSec INTEGER
        }

    ldisklogicalDiskIndex OBJECT-TYPE
        SYNTAX INTEGER
        ACCESS read-only
        STATUS mandatory
        DESCRIPTION
            "Index."
        ::= { ldisklogicalDiskEntry 1 }

    ldisklogicalDiskInstance OBJECT-TYPE
        SYNTAX DisplayString
        ACCESS read-only
        STATUS mandatory
        DESCRIPTION
            "Instance name."
        ::= { ldisklogicalDiskEntry 2 }

    ldiskPercentFreeSpace OBJECT-TYPE
        SYNTAX INTEGER
        ACCESS read-only
        STATUS mandatory
        DESCRIPTION
            "Percent Free Space is the ratio of the free space available on the logical disk unit to the total usable space provided by the selected logical disk drive"
        ::= { ldisklogicalDiskEntry 3 }

    ldiskFreeMegabytes OBJECT-TYPE
        SYNTAX INTEGER
        ACCESS read-only
        STATUS mandatory
        DESCRIPTION
            "Free Megabytes displays the unallocated space on the disk drive in megabytes. One megabyte = 1,048,576 bytes."
        ::= { ldisklogicalDiskEntry 4 }

    ldiskCurrentDiskQueueLength OBJECT-TYPE
        SYNTAX INTEGER
        ACCESS read-only
        STATUS mandatory
        DESCRIPTION
            "Current Disk Queue Length is the number of requests outstanding on the disk at the time the performance data is collected.  It includes requests in service at the time of the snapshot.  This is an instantaneous length, not an average over the time interval.  Multi-spindle disk devices can have multiple requests active at one time, but other concurrent requests are awaiting service.  This counter may reflect a transitory high or low queue length, but if there is a sustained load on the disk drive, it is likely that this will be consistently high.  Requests are experiencing delays proportional to the length of this queue minus the number of spindles on the disks.  This difference should average less than 2 for good performance."
        ::= { ldisklogicalDiskEntry 5 }

    ldiskPercentDiskTime OBJECT-TYPE
        SYNTAX TimeTicks
        ACCESS read-only
        STATUS mandatory
        DESCRIPTION
            "Disk Time is the percentage of elapsed time that the selected disk drive is busy servicing read or write requests."
        ::= { ldisklogicalDiskEntry 6 }

    ldiskAvgDiskQueueLength OBJECT-TYPE
        SYNTAX INTEGER
        ACCESS read-only
        STATUS mandatory
        DESCRIPTION
            "Avg. Disk Queue Length is the average number of both read and write requests that were queued for the selected disk during the sample interval."
        ::= { ldisklogicalDiskEntry 7 }

    ldiskPercentDiskReadTime OBJECT-TYPE
        SYNTAX TimeTicks
        ACCESS read-only
        STATUS mandatory
        DESCRIPTION
            "Disk Read Time is the percentage of elapsed time that the selected disk drive is busy servicing read requests."
        ::= { ldisklogicalDiskEntry 8 }

    ldiskAvgDiskReadQueueLength OBJECT-TYPE
        SYNTAX INTEGER
        ACCESS read-only
        STATUS mandatory
        DESCRIPTION
            "Avg. Disk Read Queue Length is the average number of read requests that were queued for the selected disk during the sample interval."
        ::= { ldisklogicalDiskEntry 9 }

    ldiskPercentDiskWriteTime OBJECT-TYPE
        SYNTAX TimeTicks
        ACCESS read-only
        STATUS mandatory
        DESCRIPTION
            "Disk Write Time is the percentage of elapsed time that the selected disk drive is busy servicing write requests."
        ::= { ldisklogicalDiskEntry 10 }

    ldiskAvgDiskWriteQueueLength OBJECT-TYPE
        SYNTAX INTEGER
        ACCESS read-only
        STATUS mandatory
        DESCRIPTION
            "Avg. Disk Write Queue Length is the average number of write requests that were queued for the selected disk during the sample interval."
        ::= { ldisklogicalDiskEntry 11 }

    ldiskAvgDiskSecPerTransfer OBJECT-TYPE
        SYNTAX TimeTicks
        ACCESS read-only
        STATUS mandatory
        DESCRIPTION
            "Avg. Disk sec/Transfer is the time in seconds of the average disk transfer."
        ::= { ldisklogicalDiskEntry 12 }

    ldiskAvgDiskSecPerRead OBJECT-TYPE
        SYNTAX TimeTicks
        ACCESS read-only
        STATUS mandatory
        DESCRIPTION
            "Avg. Disk sec/Read is the average time in seconds of a read of data from the disk."
        ::= { ldisklogicalDiskEntry 13 }

    ldiskAvgDiskSecPerWrite OBJECT-TYPE
        SYNTAX TimeTicks
        ACCESS read-only
        STATUS mandatory
        DESCRIPTION
            "Avg. Disk sec/Write is the average time in seconds of a write of data to the disk."
        ::= { ldisklogicalDiskEntry 14 }

    ldiskDiskTransfersPerSec OBJECT-TYPE
        SYNTAX Counter
        ACCESS read-only
        STATUS mandatory
        DESCRIPTION
            "Disk Transfers/sec is the rate of read and write operations on the disk."
        ::= { ldisklogicalDiskEntry 15 }

    ldiskDiskReadsPerSec OBJECT-TYPE
        SYNTAX Counter
        ACCESS read-only
        STATUS mandatory
        DESCRIPTION
            "Disk Reads/sec is the rate of read operations on the disk."
        ::= { ldisklogicalDiskEntry 16 }

    ldiskDiskWritesPerSec OBJECT-TYPE
        SYNTAX Counter
        ACCESS read-only
        STATUS mandatory
        DESCRIPTION
            "Disk Writes/sec is the rate of write operations on the disk."
        ::= { ldisklogicalDiskEntry 17 }

    ldiskDiskBytesPerSec OBJECT-TYPE
        SYNTAX INTEGER
        ACCESS read-only
        STATUS mandatory
        DESCRIPTION
            "Disk Bytes/sec is the rate bytes are transferred to or from the disk during write or read operations."
        ::= { ldisklogicalDiskEntry 18 }

    ldiskDiskReadBytesPerSec OBJECT-TYPE
        SYNTAX INTEGER
        ACCESS read-only
        STATUS mandatory
        DESCRIPTION
            "Disk Read Bytes/sec is the rate bytes are transferred from the disk during read operations."
        ::= { ldisklogicalDiskEntry 19 }

    ldiskDiskWriteBytesPerSec OBJECT-TYPE
        SYNTAX INTEGER
        ACCESS read-only
        STATUS mandatory
        DESCRIPTION
            "Disk Write Bytes is rate bytes are transferred to the disk during write operations."
        ::= { ldisklogicalDiskEntry 20 }

    -- paging File MIB

    pagefilepaging-FileTable OBJECT-TYPE
        SYNTAX SEQUENCE OF pagefilepaging-FileEntry
        ACCESS not-accessible
        STATUS mandatory
        DESCRIPTION
            "A table containing performance information for instances of 'paging-File' objects."
        ::= { performance 6 }

    pagefilepaging-FileEntry OBJECT-TYPE
        SYNTAX pagefilepaging-FileEntry
        ACCESS not-accessible
        STATUS mandatory
        DESCRIPTION
            "Performance information for one particular instance of 'paging-File' object."
        INDEX { pagefilepaging-FileIndex }
        ::= { pagefilepaging-FileTable 1 }

    pagefilepaging-FileEntry ::=
        SEQUENCE {
            pagefilepaging-FileIndex INTEGER,
            pagefilepaging-FileInstance DisplayString,
            pagefilePercentUsage INTEGER,
            pagefilePercentUsagePeak INTEGER
        }

    pagefilepaging-FileIndex OBJECT-TYPE
        SYNTAX INTEGER
        ACCESS read-only
        STATUS mandatory
        DESCRIPTION
            "Index."
        ::= { pagefilepaging-FileEntry 1 }

    pagefilepaging-FileInstance OBJECT-TYPE
        SYNTAX DisplayString
        ACCESS read-only
        STATUS mandatory
        DESCRIPTION
            "Instance name."
        ::= { pagefilepaging-FileEntry 2 }

    pagefilePercentUsage OBJECT-TYPE
        SYNTAX INTEGER
        ACCESS read-only
        STATUS mandatory
        DESCRIPTION
            "The amount of the Page File instance in use in percent.  See also Process:Page File Bytes."
        ::= { pagefilepaging-FileEntry 3 }

    pagefilePercentUsagePeak OBJECT-TYPE
        SYNTAX INTEGER
        ACCESS read-only
        STATUS mandatory
        DESCRIPTION
            "The peak usage of the Page File instance in percent.  See also Process:Page File Bytes Peak."
        ::= { pagefilepaging-FileEntry 4 }

    -- process MIB

    processprocessTable OBJECT-TYPE
        SYNTAX SEQUENCE OF processprocessEntry
        ACCESS not-accessible
        STATUS mandatory
        DESCRIPTION
            "A table containing performance information for instances of 'process' objects."
        ::= { performance 7 }

    processprocessEntry OBJECT-TYPE
        SYNTAX processprocessEntry
        ACCESS not-accessible
        STATUS mandatory
        DESCRIPTION
            "Performance information for one particular instance of 'process' object."
        INDEX { processprocessIndex }
        ::= { processprocessTable 1 }

    processprocessEntry ::=
        SEQUENCE {
            processprocessIndex INTEGER,
            processprocessInstance DisplayString,
            processPercentProcessorTime INTEGER,
            processPercentUserTime INTEGER,
            processPercentPrivilegedTime INTEGER,
            processVirtualBytesPeak INTEGER,
            processVirtualBytes INTEGER,
            processPageFaultsPerSec Counter,
            processWorkingSetPeak INTEGER,
            processWorkingSet INTEGER,
            processPageFileBytesPeak INTEGER,
            processPageFileBytes INTEGER,
            processPrivateBytes INTEGER,
            processThreadCount INTEGER,
            processPriorityBase INTEGER,
            processElapsedTime TimeTicks,
            processIDProcess INTEGER,
            processPoolPagedBytes INTEGER,
            processPoolNonpagedBytes INTEGER,
            processHandleCount INTEGER
        }

    processprocessIndex OBJECT-TYPE
        SYNTAX INTEGER
        ACCESS read-only
        STATUS mandatory
        DESCRIPTION
            "Index."
        ::= { processprocessEntry 1 }

    processprocessInstance OBJECT-TYPE
        SYNTAX DisplayString
        ACCESS read-only
        STATUS mandatory
        DESCRIPTION
            "Instance name."
        ::= { processprocessEntry 2 }

    processPercentProcessorTime OBJECT-TYPE
        SYNTAX INTEGER
        ACCESS read-only
        STATUS mandatory
        DESCRIPTION
            "Processor Time is the percentage of elapsed time that all of the threads of this process used the processor to execute instructions.  An instruction is the basic unit of execution in a computer, a thread is the object that executes instructions, and a process is the object created when a program is run.  Code executed to handle certain hardware interrupts or trap conditions may be counted for this process."
        ::= { processprocessEntry 3 }

    processPercentUserTime OBJECT-TYPE
        SYNTAX INTEGER
        ACCESS read-only
        STATUS mandatory
        DESCRIPTION
            "User Time is the percentage of elapsed time that this process's threads have spent executing code in User Mode.  Applications execute in User Mode, as do subsystems like the window manager and the graphics engine.  Code executing in User Mode cannot damage the integrity of the Windows NT Executive, Kernel, and device drivers.  Unlike some early operating systems, Windows NT uses process boundaries for subsystem protection in addition to the traditional protection of User and Privileged modes.  These subsystem processes provide additional protection.  Therefore, some work done by Windows NT on behalf of your application may appear in other subsystem processes in addition to the Privileged Time in your process."
        ::= { processprocessEntry 4 }

    processPercentPrivilegedTime OBJECT-TYPE
        SYNTAX INTEGER
        ACCESS read-only
        STATUS mandatory
        DESCRIPTION
            "Privileged Time is the percentage of elapsed time that this process's threads have spent executing code in Privileged Mode.  When a Windows NT system service is called, the service will often run in Privileged Mode to gain access to system-private data.  Such data is protected from access by threads executing in User Mode.  Calls to the system may be explicit, or they may be implicit such as when a page fault or an interrupt occurs.  Unlike some early operating systems, Windows NT uses process boundaries for subsystem protection in addition to the traditional protection of User and Privileged modes.  These subsystem processes provide additional protection.  Therefore, some work done by Windows NT on behalf of your application may appear in other subsystem processes in addition to the Privileged Time in your process."
        ::= { processprocessEntry 5 }

    processVirtualBytesPeak OBJECT-TYPE
        SYNTAX INTEGER
        ACCESS read-only
        STATUS mandatory
        DESCRIPTION
            "Virtual Bytes Peak is the maximum number of bytes of virtual address space the process has used at any one time.  Use of virtual address space does not necessarily imply corresponding use of either disk or main memory pages.  Virtual space is however finite, and by using too much, the process may limit its ability to load libraries."
        ::= { processprocessEntry 6 }

    processVirtualBytes OBJECT-TYPE
        SYNTAX INTEGER
        ACCESS read-only
        STATUS mandatory
        DESCRIPTION
            "Virtual Bytes is the current size in bytes of the virtual address space the process is using.  Use of virtual address space does not necessarily imply corresponding use of either disk or main memory pages.  Virtual space is however finite, and by using too much, the process may limit its ability to load libraries."
        ::= { processprocessEntry 7 }

    processPageFaultsPerSec OBJECT-TYPE
        SYNTAX Counter
        ACCESS read-only
        STATUS mandatory
        DESCRIPTION
            "Page Faults/sec is the rate of Page Faults by the threads executing in this process.  A page fault occurs when a thread refers to a virtual memory page that is not in its working set in main memory.  This will not cause the page to be fetched from disk if it is on the standby list and hence already in main memory, or if it is in use by another process with whom the page is shared."
        ::= { processprocessEntry 8 }

    processWorkingSetPeak OBJECT-TYPE
        SYNTAX INTEGER
        ACCESS read-only
        STATUS mandatory
        DESCRIPTION
            "Working Set Peak is the maximum number of bytes in the Working Set of this process at any point in time.  The Working Set is the set of memory pages touched recently by the threads in the process.  If free memory in the computer is above a threshold, pages are left in the Working Set of a process even if they are not in use.  When free memory falls below a threshold, pages are trimmed from Working Sets.  If they are needed they will then be soft-faulted back into the Working Set before they leave main memory."
        ::= { processprocessEntry 9 }

    processWorkingSet OBJECT-TYPE
        SYNTAX INTEGER
        ACCESS read-only
        STATUS mandatory
        DESCRIPTION
            "Working Set is the current number of bytes in the Working Set of this process.  The Working Set is the set of memory pages touched recently by the threads in the process.  If free memory in the computer is above a threshold, pages are left in the Working Set of a process even if they are not in use.  When free memory falls below a threshold, pages are trimmed from Working Sets.  If they are needed they will then be soft-faulted back into the Working Set before they leave main memory."
        ::= { processprocessEntry 10 }

    processPageFileBytesPeak OBJECT-TYPE
        SYNTAX INTEGER
        ACCESS read-only
        STATUS mandatory
        DESCRIPTION
            "Page File Bytes Peak is the maximum number of bytes this process has used in the paging file(s).  Paging files are used to store pages of memory used by the process that are not contained in other files.  Paging files are shared by all processes, and lack of space in paging files can prevent other processes from allocating memory."
        ::= { processprocessEntry 11 }

    processPageFileBytes OBJECT-TYPE
        SYNTAX INTEGER
        ACCESS read-only
        STATUS mandatory
        DESCRIPTION
            "Page File Bytes is the current number of bytes this process has used in the paging file(s).  Paging files are used to store pages of memory used by the process that are not contained in other files.  Paging files are shared by all processes, and lack of space in paging files can prevent other processes from allocating memory."
        ::= { processprocessEntry 12 }

    processPrivateBytes OBJECT-TYPE
        SYNTAX INTEGER
        ACCESS read-only
        STATUS mandatory
        DESCRIPTION
            "Private Bytes is the current number of bytes this process has allocated that cannot be shared with other processes."
        ::= { processprocessEntry 13 }

    processThreadCount OBJECT-TYPE
        SYNTAX INTEGER
        ACCESS read-only
        STATUS mandatory
        DESCRIPTION
            "The number of threads currently active in this process.  An instruction is the basic unit of execution in a processor, and a thread is the object that executes instructions.  Every running process has at least one thread."
        ::= { processprocessEntry 14 }

    processPriorityBase OBJECT-TYPE
        SYNTAX INTEGER
        ACCESS read-only
        STATUS mandatory
        DESCRIPTION
            "The current base priority of this process.  Threads within a process can raise and lower their own base priority relative to the process's base priority."
        ::= { processprocessEntry 15 }

    processElapsedTime OBJECT-TYPE
        SYNTAX TimeTicks
        ACCESS read-only
        STATUS mandatory
        DESCRIPTION
            "The total elapsed time (in seconds) this process has been running."
        ::= { processprocessEntry 16 }

    processIDProcess OBJECT-TYPE
        SYNTAX INTEGER
        ACCESS read-only
        STATUS mandatory
        DESCRIPTION
            "ID Process is the unique identifier of this process.  ID Process numbers are reused, so they only identify a process for the lifetime of that process."
        ::= { processprocessEntry 17 }

    processPoolPagedBytes OBJECT-TYPE
        SYNTAX INTEGER
        ACCESS read-only
        STATUS mandatory
        DESCRIPTION
            "Pool Paged Bytes is the number of bytes in the Paged Pool, a system memory area where space is acquired by operating system components as they accomplish their appointed tasks.  Paged Pool pages can be paged out to the paging file when not accessed by the system for sustained periods of time."
        ::= { processprocessEntry 18 }

    processPoolNonpagedBytes OBJECT-TYPE
        SYNTAX INTEGER
        ACCESS read-only
        STATUS mandatory
        DESCRIPTION
            "Pool Nonpaged Bytes is the number of bytes in the Nonpaged Pool, a system memory area where space is acquired by operating system components as they accomplish their appointed tasks.  Nonpaged Pool pages cannot be paged out to the paging file, but instead remain in main memory as long as they are allocated."
        ::= { processprocessEntry 19 }

    processHandleCount OBJECT-TYPE
        SYNTAX INTEGER
        ACCESS read-only
        STATUS mandatory
        DESCRIPTION
            "The total number of handles currently open by this process.  This number is the sum of the handles currently open by each thread in this process."
        ::= { processprocessEntry 20 }

    -- redirector MIB

    redirector OBJECT IDENTIFIER ::= { performance 8 }

    redirectorBytesTotalPerSec OBJECT-TYPE
        SYNTAX INTEGER
        ACCESS read-only
        STATUS mandatory
        DESCRIPTION
            "Bytes Total/sec is the rate the Redirector is processing data bytes.  This includes all application and file data in addition to protocol information such as packet headers."
        ::= { redirector 1 }

    redirectorFileDataOperationsPerSec OBJECT-TYPE
        SYNTAX Counter
        ACCESS read-only
        STATUS mandatory
        DESCRIPTION
            "File Data Operations/sec is the rate the Redirector is processing data operations.  One operation includes (hopefully) many bytes.  We say hopefully here because each operation has overhead.  You can determine the efficiency of this path by dividing the Bytes/sec by this counter to determine the average number of bytes transferred/operation."
        ::= { redirector 2 }

    redirectorPacketsPerSec OBJECT-TYPE
        SYNTAX INTEGER
        ACCESS read-only
        STATUS mandatory
        DESCRIPTION
            "Packets/sec is the rate the Redirector is processing data packets.  One packet includes (hopefully) many bytes.  We say hopefully here because each packet has protocol overhead.  You can determine the efficiency of this path by dividing the Bytes/sec by this counter to determine the average number of bytes transferred/packet.  You can also divide this counter by Operations/sec to determine the average number of packets per operation, another measure of efficiency."
        ::= { redirector 3 }

    redirectorBytesReceivedPerSec OBJECT-TYPE
        SYNTAX INTEGER
        ACCESS read-only
        STATUS mandatory
        DESCRIPTION
            "Bytes Received/sec is the rate of bytes coming in to the Redirector from the network.  It includes all application data as well as network protocol information (such as packet headers.)"
        ::= { redirector 4 }

    redirectorPacketsReceivedPerSec OBJECT-TYPE
        SYNTAX INTEGER
        ACCESS read-only
        STATUS mandatory
        DESCRIPTION
            "Packets Received/sec is the rate that the Redirector is receiving packets (also called SMBs or Server Message Blocks).  Network transmissions are divided into packets.  The average number of bytes received in a packet can be obtained by dividing Bytes Received/sec by this counter.  Some packets received may not contain incoming data, for example an acknowledgment to a write made by the Redirector would count as an incoming packet."
        ::= { redirector 5 }

    redirectorReadBytesPagingPerSec OBJECT-TYPE
        SYNTAX INTEGER
        ACCESS read-only
        STATUS mandatory
        DESCRIPTION
            "Read Bytes Paging/sec is the rate that the Redirector is attempting to read bytes in response to page faults.  Page faults are caused by loading of modules (such as programs and libraries), by a miss in the Cache (see Read Bytes Cache/sec), or by files directly mapped into the address space of applications (a high-performance feature of Windows NT.)"
        ::= { redirector 6 }

    redirectorReadBytesNon-PagingPerSec OBJECT-TYPE
        SYNTAX INTEGER
        ACCESS read-only
        STATUS mandatory
        DESCRIPTION
            "Read Bytes Non-Paging/sec are those bytes read by the Redirector in response to normal file requests by an application when they are redirected to come from another computer.  In addition to file requests, this counter includes other methods of reading across the network such as Named Pipes and Transactions.  This counter does not count network protocol information, just application data."
        ::= { redirector 7 }

    redirectorReadBytesCachePerSec OBJECT-TYPE
        SYNTAX INTEGER
        ACCESS read-only
        STATUS mandatory
        DESCRIPTION
            "Read Bytes Cache/sec is the rate that applications on your computer are accessing the Cache using the Redirector.  Some of these data requests may be satisfied by merely retrieving the data from the system Cache on your own computer if it happened to be used recently and there was room to keep it in the Cache.  Requests that miss the Cache will cause a page fault (see Read Bytes Paging/sec)."
        ::= { redirector 8 }

    redirectorReadBytesNetworkPerSec OBJECT-TYPE
        SYNTAX INTEGER
        ACCESS read-only
        STATUS mandatory
        DESCRIPTION
            "Read Bytes Network/sec is the rate that applications are reading data across the network.  For one reason or another the data was not in the system Cache, and these bytes actually came across the network.  Dividing this number by Bytes Received/sec will indicate the 'efficiency' of data coming in from the network, since all of these bytes are real application data (see Bytes Received/sec.)"
        ::= { redirector 9 }

    redirectorBytesTransmittedPerSec OBJECT-TYPE
        SYNTAX INTEGER
        ACCESS read-only
        STATUS mandatory
        DESCRIPTION
            "Bytes Transmitted/sec is the rate that bytes are leaving the Redirector to the network.  It includes all application data as well as network protocol information (such as packet headers and the like.)"
        ::= { redirector 10 }

    redirectorPacketsTransmittedPerSec OBJECT-TYPE
        SYNTAX INTEGER
        ACCESS read-only
        STATUS mandatory
        DESCRIPTION
            "Packets Transmitted/sec is the rate that the Redirector is sending packets (also called SMBs or Server Message Blocks).  Network transmissions are divided into packets.  The average number of bytes transmitted in a packet can be obtained by dividing Bytes Transmitted/sec by this counter."
        ::= { redirector 11 }

    redirectorWriteBytesPagingPerSec OBJECT-TYPE
        SYNTAX INTEGER
        ACCESS read-only
        STATUS mandatory
        DESCRIPTION
            "Write Bytes Paging/sec is the rate that the Redirector is attempting to write bytes changed in the pages being used by applications.  The program data changed by modules (such as programs and libraries) that were loaded over the network are 'paged out' when no longer needed.  Other output pages come from the Cache (see Write Bytes Cache/sec)."
        ::= { redirector 12 }

    redirectorWriteBytesNon-PagingPerSec OBJECT-TYPE
        SYNTAX INTEGER
        ACCESS read-only
        STATUS mandatory
        DESCRIPTION
            "Write Bytes Non-Paging/sec is the rate of the bytes that are written by the Redirector in response to normal file outputs by an application when they are redirected to go to another computer.  In addition to file requests this counter includes other methods of writing across the network such as Named Pipes and Transactions.  This counter does not count network protocol information, just application data."
        ::= { redirector 13 }

    redirectorWriteBytesCachePerSec OBJECT-TYPE
        SYNTAX INTEGER
        ACCESS read-only
        STATUS mandatory
        DESCRIPTION
            "Write Bytes Cache/sec is the rate that applications on your computer are writing to the Cache using the Redirector.  The data may not leave your computer immediately, but may be retained in the Cache for further modification before being written to the network.  This saves network traffic.  Each write of a byte into the Cache is counted here."
        ::= { redirector 14 }

    redirectorWriteBytesNetworkPerSec OBJECT-TYPE
        SYNTAX INTEGER
        ACCESS read-only
        STATUS mandatory
        DESCRIPTION
            "Write Bytes Network/sec is the rate that your applications are writing data across the network.  Either the system Cache was bypassed, as for Named Pipes or Transactions, or else the Cache wrote the bytes to make room for other data.  Dividing this counter by Bytes Transmitted/sec will indicate the 'efficiency' of data written to the network, since all of these bytes are real application data (see Transmitted Bytes/sec.)"
        ::= { redirector 15 }

    redirectorFileReadOperationsPerSec OBJECT-TYPE
        SYNTAX Counter
        ACCESS read-only
        STATUS mandatory
        DESCRIPTION
            "File Read Operations/sec is the rate that applications are asking the Redirector for data.  Each call to a file system or similar Application Program Interface (API) call counts as one operation."
        ::= { redirector 16 }

    redirectorReadOperationsRandomPerSec OBJECT-TYPE
        SYNTAX Counter
        ACCESS read-only
        STATUS mandatory
        DESCRIPTION
            "Read Operations Random/sec counts the rate that, on a file-by-file basis, reads are made that are not sequential.  If a read is made using a particular file handle, and then is followed by another read that is not immediately the contiguous next byte, this counter is incremented by one."
        ::= { redirector 17 }

    redirectorReadPacketsPerSec OBJECT-TYPE
        SYNTAX Counter
        ACCESS read-only
        STATUS mandatory
        DESCRIPTION
            "Read Packets/sec is the rate that read packets are being placed on the network.  Each time a single packet is sent with a request to read data remotely, this counter is incremented by one."
        ::= { redirector 18 }

    redirectorReadsLargePerSec OBJECT-TYPE
        SYNTAX Counter
        ACCESS read-only
        STATUS mandatory
        DESCRIPTION
            "Reads Large/sec is the rate that reads over 2 times the server's negotiated buffer size are made by applications.  Too many of these could place a strain on server resources.  This counter is incremented once for each read. It does not count packets."
        ::= { redirector 19 }

    redirectorReadPacketsSmallPerSec OBJECT-TYPE
        SYNTAX Counter
        ACCESS read-only
        STATUS mandatory
        DESCRIPTION
            "Read Packets Small/sec is the rate that reads less than one-fourth of the server's negotiated buffer size are made by applications.  Too many of these could indicate a waste of buffers on the server.  This counter is incremented once for each read. It does not count packets."
        ::= { redirector 20 }

    redirectorFileWriteOperationsPerSec OBJECT-TYPE
        SYNTAX Counter
        ACCESS read-only
        STATUS mandatory
        DESCRIPTION
            "File Write Operations/sec is the rate that applications are sending data to the Redirector.  Each call to a file system or similar Application Program Interface (API) call counts as one operation."
        ::= { redirector 21 }

    redirectorWriteOperationsRandomPerSec OBJECT-TYPE
        SYNTAX Counter
        ACCESS read-only
        STATUS mandatory
        DESCRIPTION
            "Write Operations Random/sec is the rate that, on a file-by-file basis, writes are made that are not sequential.  If a write is made using a particular file handle, and then is followed by another write that is not immediately the next contiguous byte, this counter is incremented by one."
        ::= { redirector 22 }

    redirectorWritePacketsPerSec OBJECT-TYPE
        SYNTAX Counter
        ACCESS read-only
        STATUS mandatory
        DESCRIPTION
            "Write Packets/sec is the rate that writes are being sent to the network.  Each time a single packet is sent with a request to write remote data, this counter is incremented by one."
        ::= { redirector 23 }

    redirectorWritesLargePerSec OBJECT-TYPE
        SYNTAX Counter
        ACCESS read-only
        STATUS mandatory
        DESCRIPTION
            "Writes Large/sec is the rate that writes are made by applications that are over 2 times the server's negotiated buffer size.  Too many of these could place a strain on server resources.  This counter is incremented once for each write: it counts writes, not packets."
        ::= { redirector 24 }

    redirectorWritePacketsSmallPerSec OBJECT-TYPE
        SYNTAX Counter
        ACCESS read-only
        STATUS mandatory
        DESCRIPTION
            "Write Packets Small/sec is the rate that writes are made by applications that are less than one-fourth of the server's negotiated buffer size.  Too many of these could indicate a waste of buffers on the server.  This counter is incremented once for each write: it counts writes, not packets!"
        ::= { redirector 25 }

    redirectorReadsDeniedPerSec OBJECT-TYPE
        SYNTAX Counter
        ACCESS read-only
        STATUS mandatory
        DESCRIPTION
            "Reads Denied/sec is the rate that the server is unable to accommodate requests for Raw Reads.  When a read is much larger than the server's negotiated buffer size, the Redirector requests a Raw Read which, if granted, would permit the transfer of the data without lots of protocol overhead on each packet.  To accomplish this the server must lock out other requests, so the request is denied if the server is really busy."
        ::= { redirector 26 }

    redirectorWritesDeniedPerSec OBJECT-TYPE
        SYNTAX Counter
        ACCESS read-only
        STATUS mandatory
        DESCRIPTION
            "Writes Denied/sec is the rate that the server is unable to accommodate requests for Raw Writes.  When a write is much larger than the server's negotiated buffer size, the Redirector requests a Raw Write which, if granted, would permit the transfer of the data without lots of protocol overhead on each packet.  To accomplish this the server must lock out other requests, so the request is denied if the server is really busy."
        ::= { redirector 27 }

    redirectorNetworkErrorsPerSec OBJECT-TYPE
        SYNTAX Counter
        ACCESS read-only
        STATUS mandatory
        DESCRIPTION
            "Network Errors/sec counts serious unexpected errors that generally indicate the Redirector and one or more Servers are having serious communication difficulties.  For example an SMB (Server Manager Block) protocol error will generate a Network Error.  These result in an entry in the system Event Log, so look there for details."
        ::= { redirector 28 }

    redirectorServerSessions OBJECT-TYPE
        SYNTAX INTEGER
        ACCESS read-only
        STATUS mandatory
        DESCRIPTION
            "Server Sessions counts the total number of security objects the Redirector has managed.  For example, a Logon to a server followed by a network access to the same server will establish one connection, but two sessions."
        ::= { redirector 29 }

    redirectorServerReconnects OBJECT-TYPE
        SYNTAX INTEGER
        ACCESS read-only
        STATUS mandatory
        DESCRIPTION
            "Server Reconnects counts the number of times your Redirector has had to reconnect to a server in order to complete a new active request.  You can be disconnected by the Server if you remain inactive for too long.  Locally even if all your remote files are closed, the Redirector will keep your connections intact for (nominally) ten minutes.  Such inactive connections are called Dormant Connections.  Reconnecting is expensive in time."
        ::= { redirector 30 }

    redirectorConnectsCore OBJECT-TYPE
        SYNTAX INTEGER
        ACCESS read-only
        STATUS mandatory
        DESCRIPTION
            "Connects Core counts the number of connections you have to servers running the original MS-Net SMB protocol, including MS-Net itself and Xenix and Vax's."
        ::= { redirector 31 }

    redirectorConnectsLanManager20 OBJECT-TYPE
        SYNTAX INTEGER
        ACCESS read-only
        STATUS mandatory
        DESCRIPTION
            "Connects Lan Manager 2.0 counts connections to Lan Manager 2.0 servers, including LMX servers."
        ::= { redirector 32 }

    redirectorConnectsLanManager21 OBJECT-TYPE
        SYNTAX INTEGER
        ACCESS read-only
        STATUS mandatory
        DESCRIPTION
            "Connects Lan Manager 2.1 counts connections to Lan Manager 2.1 servers, including LMX servers."
        ::= { redirector 33 }

    redirectorConnectsWindowsNT OBJECT-TYPE
        SYNTAX INTEGER
        ACCESS read-only
        STATUS mandatory
        DESCRIPTION
            "Connects Windows NT counts the connections to Windows NT computers.  Good choice!"
        ::= { redirector 34 }

    redirectorServerDisconnects OBJECT-TYPE
        SYNTAX INTEGER
        ACCESS read-only
        STATUS mandatory
        DESCRIPTION
            "Server Disconnects counts the number of times a Server has disconnected your Redirector.  See also Server Reconnects."
        ::= { redirector 35 }

    redirectorServerSessionsHung OBJECT-TYPE
        SYNTAX INTEGER
        ACCESS read-only
        STATUS mandatory
        DESCRIPTION
            "Server Sessions Hung counts the number of active sessions that are timed out and unable to proceed due to a lack of response from the remote server."
        ::= { redirector 36 }

    redirectorCurrentCommands OBJECT-TYPE
        SYNTAX INTEGER
        ACCESS read-only
        STATUS mandatory
        DESCRIPTION
            "Current Commands counts the number of requests to the Redirector that are currently queued for service.  If this number is much larger than the number of network adapter cards installed in the computer, then the network(s) and/or the server(s) being accessed are seriously bottlenecked."
        ::= { redirector 37 }

    -- tCP MIB

    tCP OBJECT IDENTIFIER ::= { performance 9 }

    tcpSegmentsPerSec OBJECT-TYPE
        SYNTAX Counter
        ACCESS read-only
        STATUS mandatory
        DESCRIPTION
            "Segments/sec is the rate that TCP segments are sent or received using the TCP protocol."
        ::= { tCP 1 }

    tcpConnectionsEstablished OBJECT-TYPE
        SYNTAX INTEGER
        ACCESS read-only
        STATUS mandatory
        DESCRIPTION
            "Connections Established is the number of TCP connections for which the current state is either ESTABLISHED or CLOSE-WAIT."
        ::= { tCP 2 }

    tcpConnectionsActive OBJECT-TYPE
        SYNTAX INTEGER
        ACCESS read-only
        STATUS mandatory
        DESCRIPTION
            "Connections Active is the number of times TCP connections have made a direct transition to the SYN-SENT state from the CLOSED state."
        ::= { tCP 3 }

    tcpConnectionsPassive OBJECT-TYPE
        SYNTAX INTEGER
        ACCESS read-only
        STATUS mandatory
        DESCRIPTION
            "Connections Passive is the number of times TCP connections have made a direct transition to the SYN-RCVD state from the LISTEN state."
        ::= { tCP 4 }

    tcpConnectionFailures OBJECT-TYPE
        SYNTAX INTEGER
        ACCESS read-only
        STATUS mandatory
        DESCRIPTION
            "Connection Failures is the number of times TCP connections have made a direct transition to the CLOSED state from the SYN-SENT state or the SYN-RCVD state, plus the number of times TCP connections have made a direct transition to the LISTEN state from the SYN-RCVD state."
        ::= { tCP 5 }

    tcpConnectionsReset OBJECT-TYPE
        SYNTAX INTEGER
        ACCESS read-only
        STATUS mandatory
        DESCRIPTION
            "Connections Reset is the number of times TCP connections have made a direct transition to the CLOSED state from either the ESTABLISHED state or the CLOSE-WAIT state."
        ::= { tCP 6 }

    tcpSegmentsReceivedPerSec OBJECT-TYPE
        SYNTAX Counter
        ACCESS read-only
        STATUS mandatory
        DESCRIPTION
            "Segments Received/sec is the rate that segments are received, including those received in error.  This count includes segments received on currently established connections."
        ::= { tCP 7 }

    tcpSegmentsSentPerSec OBJECT-TYPE
        SYNTAX Counter
        ACCESS read-only
        STATUS mandatory
        DESCRIPTION
            "Segments Sent/sec is the rate that segments are sent, including those on current connections, but excluding those containing only retransmitted bytes."
        ::= { tCP 8 }

    tcpSegmentsRetransmittedPerSec OBJECT-TYPE
        SYNTAX Counter
        ACCESS read-only
        STATUS mandatory
        DESCRIPTION
            "Segments Retransmitted/sec is the rate that segments are retransmitted, that is, segments transmitted containing one or more previously transmitted bytes."
        ::= { tCP 9 }

    -- iP MIB

    iP OBJECT IDENTIFIER ::= { performance 10 }

    ipDatagramsPerSec OBJECT-TYPE
        SYNTAX Counter
        ACCESS read-only
        STATUS mandatory
        DESCRIPTION
            "Datagrams/sec is the rate that IP datagrams are received from or sent to the interfaces, including those in error.  Any forwarded datagrams are not included in this rate."
        ::= { iP 1 }

    ipDatagramsReceivedPerSec OBJECT-TYPE
        SYNTAX Counter
        ACCESS read-only
        STATUS mandatory
        DESCRIPTION
            "Datagrams Received/sec is the rate that IP datagrams are received from the interfaces, including those in error."
        ::= { iP 2 }

    ipDatagramsReceivedHeaderErrors OBJECT-TYPE
        SYNTAX INTEGER
        ACCESS read-only
        STATUS mandatory
        DESCRIPTION
            "Datagrams Received Header Errors is the number of input datagrams discarded due to errors in their IP headers, including bad checksums, version number mismatch, other format errors, time-to-live exceeded, errors discovered in processing their IP options, etc."
        ::= { iP 3 }

    ipDatagramsReceivedAddressErrors OBJECT-TYPE
        SYNTAX INTEGER
        ACCESS read-only
        STATUS mandatory
        DESCRIPTION
            "Datagrams Received Address Errors is the number of input datagrams discarded because the IP address in their IP header's destination field was not a valid address to be received at this entity.  This count includes invalid addresses (e.g., 0.0.  0.0) and addresses of unsupported Classes (e.g., Class E).  For entities that are not IP Gateways and therefore do not forward datagrams, this counter includes datagrams discarded because the destination address was not a local address."
        ::= { iP 4 }

    ipDatagramsForwardedPerSec OBJECT-TYPE
        SYNTAX Counter
        ACCESS read-only
        STATUS mandatory
        DESCRIPTION
            "Datagrams Forwarded/sec is the rate of input datagrams for that this entity was not their final IP destination, as a result of which an attempt was made to find a route to forward them to that final destination.  In entities that do not act as IP Gateways, this rate will include only those packets that were Source-Routed via this entity, and the Source-Route option processing was successful."
        ::= { iP 5 }

    ipDatagramsReceivedUnknownProtocol OBJECT-TYPE
        SYNTAX INTEGER
        ACCESS read-only
        STATUS mandatory
        DESCRIPTION
            "Datagrams Received Unknown Protocol is the number of locally-addressed datagrams received successfully but discarded because of an unknown or unsupported protocol."
        ::= { iP 6 }

    ipDatagramsReceivedDiscarded OBJECT-TYPE
        SYNTAX INTEGER
        ACCESS read-only
        STATUS mandatory
        DESCRIPTION
            "Datagrams Received Discarded is the number of input IP datagrams for which no problems were encountered to prevent their continued processing, but which were discarded (e.g., for lack of buffer space). This counter does not include any datagrams discarded while awaiting re-assembly."
        ::= { iP 7 }

    ipDatagramsReceivedDeliveredPerSec OBJECT-TYPE
        SYNTAX Counter
        ACCESS read-only
        STATUS mandatory
        DESCRIPTION
            "Datagrams Received Delivered/sec is the rate that input datagrams are successfully delivered to IP user-protocols (including ICMP)."
        ::= { iP 8 }

    ipDatagramsSentPerSec OBJECT-TYPE
        SYNTAX Counter
        ACCESS read-only
        STATUS mandatory
        DESCRIPTION
            "Datagrams Sent/sec is the rate that IP datagrams are supplied to IP for transmission by local IP user-protocols (including ICMP). That this counter does not include any datagrams counted in Datagrams Forwarded."
        ::= { iP 9 }

    ipDatagramsOutboundDiscarded OBJECT-TYPE
        SYNTAX INTEGER
        ACCESS read-only
        STATUS mandatory
        DESCRIPTION
            "Datagrams Outbound Discarded is the number of output IP datagrams for which no problems were encountered to prevent their transmission to their destination, but which were discarded (e.g., for lack of buffer space.)  This counter would include datagrams counted in Datagrams Forwarded if any such packets met this (discretionary) discard criterion."
        ::= { iP 10 }

    ipDatagramsOutboundNoRoute OBJECT-TYPE
        SYNTAX INTEGER
        ACCESS read-only
        STATUS mandatory
        DESCRIPTION
            "Datagrams Outbound No Route is the number of IP datagrams discarded because no route could be found to transmit them to their destination. This counter includes any packets counted in Datagrams Forwarded that meet this `no route' criterion."
        ::= { iP 11 }

    ipFragmentsReceivedPerSec OBJECT-TYPE
        SYNTAX Counter
        ACCESS read-only
        STATUS mandatory
        DESCRIPTION
            "Fragments Received/sec is the rate that IP fragments that need to be re-assembled at this entity are received."
        ::= { iP 12 }

    ipFragmentsRe-assembledPerSec OBJECT-TYPE
        SYNTAX Counter
        ACCESS read-only
        STATUS mandatory
        DESCRIPTION
            "Fragments Re-assembled/sec is the rate that IP fragments are successfully re-assembled."
        ::= { iP 13 }

    ipFragmentRe-assemblyFailures OBJECT-TYPE
        SYNTAX INTEGER
        ACCESS read-only
        STATUS mandatory
        DESCRIPTION
            "Fragment Re-assembly Failures is the number of failures detected by the IP re-assembly algorithm (for whatever reason: timed out, errors, etc.)  This is not necessarily a count of discarded IP fragments since some algorithms (notably RFC 815) can lose track of the number of fragments by combining them as they are received."
        ::= { iP 14 }

    ipFragmentedDatagramsPerSec OBJECT-TYPE
        SYNTAX Counter
        ACCESS read-only
        STATUS mandatory
        DESCRIPTION
            "Fragmented Datagrams/sec is the rate that datagrams are successfully fragmented at this entity."
        ::= { iP 15 }

    ipFragmentationFailures OBJECT-TYPE
        SYNTAX INTEGER
        ACCESS read-only
        STATUS mandatory
        DESCRIPTION
            "Fragmentation Failures is the number of IP datagrams that have been discarded because they needed to be fragmented at this entity but could not be, e.g., because their `Don't Fragment' flag was set."
        ::= { iP 16 }

    ipFragmentsCreatedPerSec OBJECT-TYPE
        SYNTAX Counter
        ACCESS read-only
        STATUS mandatory
        DESCRIPTION
            "Fragments Created/sec is the rate that IP datagram fragments have been generated as a result of fragmentation at this entity."
        ::= { iP 17 }

    -- uDP MIB

    uDP OBJECT IDENTIFIER ::= { performance 11 }

    udpDatagramsPerSec OBJECT-TYPE
        SYNTAX Counter
        ACCESS read-only
        STATUS mandatory
        DESCRIPTION
            "Datagrams/sec is the rate that UDP datagrams are sent or received by the entity."
        ::= { uDP 1 }

    udpDatagramsReceivedPerSec OBJECT-TYPE
        SYNTAX Counter
        ACCESS read-only
        STATUS mandatory
        DESCRIPTION
            "Datagrams Received/sec is the rate that UDP datagrams are delivered to UDP users."
        ::= { uDP 2 }

    udpDatagramsNoPortPerSec OBJECT-TYPE
        SYNTAX Counter
        ACCESS read-only
        STATUS mandatory
        DESCRIPTION
            "Datagrams No Port/sec is the rate of received UDP datagrams for which there was no application at the destination port."
        ::= { uDP 3 }

    udpDatagramsReceivedErrors OBJECT-TYPE
        SYNTAX INTEGER
        ACCESS read-only
        STATUS mandatory
        DESCRIPTION
            "Datagrams Received Errors is the number of received UDP datagrams that could not be delivered for reasons other than the lack of an application at the destination port."
        ::= { uDP 4 }

    udpDatagramsSentPerSec OBJECT-TYPE
        SYNTAX Counter
        ACCESS read-only
        STATUS mandatory
        DESCRIPTION
            "Datagrams Sent/sec is the rate that UDP datagrams are sent from the entity."
        ::= { uDP 5 }

    -- netBEUI MIB

    netbeuinetBEUITable OBJECT-TYPE
        SYNTAX SEQUENCE OF netbeuinetBEUIEntry
        ACCESS not-accessible
        STATUS mandatory
        DESCRIPTION
            "A table containing performance information for instances of 'netBEUI' objects."
        ::= { performance 12 }

    netbeuinetBEUIEntry OBJECT-TYPE
        SYNTAX netbeuinetBEUIEntry
        ACCESS not-accessible
        STATUS mandatory
        DESCRIPTION
            "Performance information for one particular instance of 'netBEUI' object."
        INDEX { netbeuinetBEUIIndex }
        ::= { netbeuinetBEUITable 1 }

    netbeuinetBEUIEntry ::=
        SEQUENCE {
            netbeuinetBEUIIndex INTEGER,
            netbeuinetBEUIInstance DisplayString,
            netbeuiDatagramsPerSec Counter,
            netbeuiDatagramBytesPerSec INTEGER,
            netbeuiPacketsPerSec Counter,
            netbeuiFramesPerSec Counter,
            netbeuiFrameBytesPerSec INTEGER,
            netbeuiBytesTotalPerSec INTEGER,
            netbeuiConnectionsOpen INTEGER,
            netbeuiConnectionsNoRetries INTEGER,
            netbeuiConnectionsWithRetries INTEGER,
            netbeuiDisconnectsLocal INTEGER,
            netbeuiDisconnectsRemote INTEGER,
            netbeuiFailuresLink INTEGER,
            netbeuiFailuresAdapter INTEGER,
            netbeuiConnectionSessionTimeouts INTEGER,
            netbeuiConnectionsCanceled INTEGER,
            netbeuiFailuresResourceRemote INTEGER,
            netbeuiFailuresResourceLocal INTEGER,
            netbeuiFailuresNotFound INTEGER,
            netbeuiFailuresNoListen INTEGER,
            netbeuiDatagramsSentPerSec Counter,
            netbeuiDatagramBytesSentPerSec INTEGER,
            netbeuiDatagramsReceivedPerSec Counter,
            netbeuiDatagramBytesReceivedPerSec INTEGER,
            netbeuiPacketsSentPerSec Counter,
            netbeuiPacketsReceivedPerSec Counter,
            netbeuiFramesSentPerSec Counter,
            netbeuiFrameBytesSentPerSec INTEGER,
            netbeuiFramesReceivedPerSec Counter,
            netbeuiFrameBytesReceivedPerSec INTEGER,
            netbeuiFramesRe-SentPerSec Counter,
            netbeuiFrameBytesRe-SentPerSec INTEGER,
            netbeuiFramesRejectedPerSec Counter,
            netbeuiFrameBytesRejectedPerSec INTEGER,
            netbeuiExpirationsResponse INTEGER,
            netbeuiExpirationsAck INTEGER,
            netbeuiWindowSendMaximum INTEGER,
            netbeuiWindowSendAverage INTEGER,
            netbeuiPiggybackAckQueuedPerSec Counter,
            netbeuiPiggybackAckTimeouts INTEGER
        }

    netbeuinetBEUIIndex OBJECT-TYPE
        SYNTAX INTEGER
        ACCESS read-only
        STATUS mandatory
        DESCRIPTION
            "Index."
        ::= { netbeuinetBEUIEntry 1 }

    netbeuinetBEUIInstance OBJECT-TYPE
        SYNTAX DisplayString
        ACCESS read-only
        STATUS mandatory
        DESCRIPTION
            "Instance name."
        ::= { netbeuinetBEUIEntry 2 }

    netbeuiDatagramsPerSec OBJECT-TYPE
        SYNTAX Counter
        ACCESS read-only
        STATUS mandatory
        DESCRIPTION
            "Datagrams/sec is the rate that datagrams are processed by the computer.  This counter displays the sum of datagrams sent and datagrams received.  A datagram is a connectionless packet whose delivery to a remote is not guaranteed."
        ::= { netbeuinetBEUIEntry 3 }

    netbeuiDatagramBytesPerSec OBJECT-TYPE
        SYNTAX INTEGER
        ACCESS read-only
        STATUS mandatory
        DESCRIPTION
            "Datagram Bytes/sec is the rate that datagram bytes are processed by the computer.  This counter is the sum of datagram bytes that are sent as well as received.  A datagram is a connectionless packet whose delivery to a remote is not guaranteed."
        ::= { netbeuinetBEUIEntry 4 }

    netbeuiPacketsPerSec OBJECT-TYPE
        SYNTAX Counter
        ACCESS read-only
        STATUS mandatory
        DESCRIPTION
            "Packets/sec is the rate that packets are processed by the computer.  This count is the sum of Packets Sent and Packets Received per second.  This counter includes all packets processed: control as well as data packets."
        ::= { netbeuinetBEUIEntry 5 }

    netbeuiFramesPerSec OBJECT-TYPE
        SYNTAX Counter
        ACCESS read-only
        STATUS mandatory
        DESCRIPTION
            "Frames/sec is the rate that data frames (or packets) are processed by the computer.  This counter is the sum of data frames sent and data frames received.  This counter only counts those frames (packets) that carry data."
        ::= { netbeuinetBEUIEntry 6 }

    netbeuiFrameBytesPerSec OBJECT-TYPE
        SYNTAX INTEGER
        ACCESS read-only
        STATUS mandatory
        DESCRIPTION
            "Frame Bytes/sec is the rate that data bytes are processed by the computer.  This counter is the sum of data frame bytes sent and received.  This counter only counts the byte in frames (packets) that carry data."
        ::= { netbeuinetBEUIEntry 7 }

    netbeuiBytesTotalPerSec OBJECT-TYPE
        SYNTAX INTEGER
        ACCESS read-only
        STATUS mandatory
        DESCRIPTION
            "Bytes Total/sec is the sum of Frame Bytes/sec and Datagram Bytes/sec.  This is the total rate of bytes sent to or received from the network by the protocol, but only counts the bytes in frames (i.e., packets) which carry data."
        ::= { netbeuinetBEUIEntry 8 }

    netbeuiConnectionsOpen OBJECT-TYPE
        SYNTAX INTEGER
        ACCESS read-only
        STATUS mandatory
        DESCRIPTION
            "Connections Open is the number of connections currently open for this protocol.  This counter shows the current count only and does not accumulate over time."
        ::= { netbeuinetBEUIEntry 9 }

    netbeuiConnectionsNoRetries OBJECT-TYPE
        SYNTAX INTEGER
        ACCESS read-only
        STATUS mandatory
        DESCRIPTION
            "Connections No Retries is the total count of connections that were successfully made on the first try.  This number is an accumulator and shows a running total."
        ::= { netbeuinetBEUIEntry 10 }

    netbeuiConnectionsWithRetries OBJECT-TYPE
        SYNTAX INTEGER
        ACCESS read-only
        STATUS mandatory
        DESCRIPTION
            "Connections With Retries is the total count of connections that were made after retrying the attempt.  A retry occurs when the first connection attempt failed.  This number is an accumulator and shows a running total."
        ::= { netbeuinetBEUIEntry 11 }

    netbeuiDisconnectsLocal OBJECT-TYPE
        SYNTAX INTEGER
        ACCESS read-only
        STATUS mandatory
        DESCRIPTION
            "Disconnects Local is the number of session disconnections that were initiated by the local computer.  This number is an accumulator and shows a running total."
        ::= { netbeuinetBEUIEntry 12 }

    netbeuiDisconnectsRemote OBJECT-TYPE
        SYNTAX INTEGER
        ACCESS read-only
        STATUS mandatory
        DESCRIPTION
            "Disconnects Remote is the number of session disconnections that were initiated by the remote computer.  This number is an accumulator and shows a running total."
        ::= { netbeuinetBEUIEntry 13 }

    netbeuiFailuresLink OBJECT-TYPE
        SYNTAX INTEGER
        ACCESS read-only
        STATUS mandatory
        DESCRIPTION
            "Failures Link is the number of connections that were dropped due to a link failure.  This number is an accumulator and shows a running total."
        ::= { netbeuinetBEUIEntry 14 }

    netbeuiFailuresAdapter OBJECT-TYPE
        SYNTAX INTEGER
        ACCESS read-only
        STATUS mandatory
        DESCRIPTION
            "Failures Adapter is the number of connections that were dropped due to an adapter failure.  This number is an accumulator and shows a running total."
        ::= { netbeuinetBEUIEntry 15 }

    netbeuiConnectionSessionTimeouts OBJECT-TYPE
        SYNTAX INTEGER
        ACCESS read-only
        STATUS mandatory
        DESCRIPTION
            "Connection Session Timeouts is the number of connections that were dropped due to a session timeout.  This number is an accumulator and shows a running total."
        ::= { netbeuinetBEUIEntry 16 }

    netbeuiConnectionsCanceled OBJECT-TYPE
        SYNTAX INTEGER
        ACCESS read-only
        STATUS mandatory
        DESCRIPTION
            "Connections Canceled is the number of connections that were canceled.  This number is an accumulator and shows a running total."
        ::= { netbeuinetBEUIEntry 17 }

    netbeuiFailuresResourceRemote OBJECT-TYPE
        SYNTAX INTEGER
        ACCESS read-only
        STATUS mandatory
        DESCRIPTION
            "Failures Resource Remote is the number of connections that failed because of resource problems or shortages on the remote computer.  This number is an accumulator and shows a running total."
        ::= { netbeuinetBEUIEntry 18 }

    netbeuiFailuresResourceLocal OBJECT-TYPE
        SYNTAX INTEGER
        ACCESS read-only
        STATUS mandatory
        DESCRIPTION
            "Failures Resource Local is the number of connections that failed because of resource problems or shortages on the local computer.  This number is an accumulator and shows a running total."
        ::= { netbeuinetBEUIEntry 19 }

    netbeuiFailuresNotFound OBJECT-TYPE
        SYNTAX INTEGER
        ACCESS read-only
        STATUS mandatory
        DESCRIPTION
            "Failures Not Found is the number of connection attempts that failed because the remote computer could not be found.  This number is an accumulator and shows a running total."
        ::= { netbeuinetBEUIEntry 20 }

    netbeuiFailuresNoListen OBJECT-TYPE
        SYNTAX INTEGER
        ACCESS read-only
        STATUS mandatory
        DESCRIPTION
            "Failures No Listen is the number of connections that were rejected because the remote computer was not listening for connection requests."
        ::= { netbeuinetBEUIEntry 21 }

    netbeuiDatagramsSentPerSec OBJECT-TYPE
        SYNTAX Counter
        ACCESS read-only
        STATUS mandatory
        DESCRIPTION
            "Datagrams Sent/sec is the rate that datagrams are sent from the computer.  A datagram is a connectionless packet whose delivery to a remote computer is not guaranteed."
        ::= { netbeuinetBEUIEntry 22 }

    netbeuiDatagramBytesSentPerSec OBJECT-TYPE
        SYNTAX INTEGER
        ACCESS read-only
        STATUS mandatory
        DESCRIPTION
            "Datagram Bytes Sent/sec is the rate that datagram bytes are sent from the computer.  A datagram is a connectionless packet whose delivery to a remote computer is not guaranteed."
        ::= { netbeuinetBEUIEntry 23 }

    netbeuiDatagramsReceivedPerSec OBJECT-TYPE
        SYNTAX Counter
        ACCESS read-only
        STATUS mandatory
        DESCRIPTION
            "Datagrams Received/sec is the rate that datagrams are received by the computer.  A datagram is a connectionless packet whose delivery to a remote computer is not guaranteed."
        ::= { netbeuinetBEUIEntry 24 }

    netbeuiDatagramBytesReceivedPerSec OBJECT-TYPE
        SYNTAX INTEGER
        ACCESS read-only
        STATUS mandatory
        DESCRIPTION
            "Datagram Bytes Received/sec is the rate that datagram bytes are received by the computer.  A datagram is a connectionless packet whose delivery to a remote computer is not guaranteed."
        ::= { netbeuinetBEUIEntry 25 }

    netbeuiPacketsSentPerSec OBJECT-TYPE
        SYNTAX Counter
        ACCESS read-only
        STATUS mandatory
        DESCRIPTION
            "Packets Sent/sec is the rate that packets are sent by the computer.  This counter counts all packets sent by the computer, i.e. control as well as data packets."
        ::= { netbeuinetBEUIEntry 26 }

    netbeuiPacketsReceivedPerSec OBJECT-TYPE
        SYNTAX Counter
        ACCESS read-only
        STATUS mandatory
        DESCRIPTION
            "Packets Received/sec is the rate that packets are received by the computer.  This counter counts all packets processed: control as well as data packets."
        ::= { netbeuinetBEUIEntry 27 }

    netbeuiFramesSentPerSec OBJECT-TYPE
        SYNTAX Counter
        ACCESS read-only
        STATUS mandatory
        DESCRIPTION
            "Frames Sent/sec is the rate that data frames are sent by the computer.  This counter only counts the frames (packets) that carry data."
        ::= { netbeuinetBEUIEntry 28 }

    netbeuiFrameBytesSentPerSec OBJECT-TYPE
        SYNTAX INTEGER
        ACCESS read-only
        STATUS mandatory
        DESCRIPTION
            "Frame Bytes Sent/sec is the rate that data bytes are sent by the computer.  This counter only counts the bytes in frames (packets) that carry data."
        ::= { netbeuinetBEUIEntry 29 }

    netbeuiFramesReceivedPerSec OBJECT-TYPE
        SYNTAX Counter
        ACCESS read-only
        STATUS mandatory
        DESCRIPTION
            "Frames Received/sec is the rate that data frames are received by the computer.  This counter only counts the frames (packets) that carry data."
        ::= { netbeuinetBEUIEntry 30 }

    netbeuiFrameBytesReceivedPerSec OBJECT-TYPE
        SYNTAX INTEGER
        ACCESS read-only
        STATUS mandatory
        DESCRIPTION
            "Frame Bytes Received/sec is the rate that data bytes are received by the computer.  This counter only counts the frames (packets) that carry data."
        ::= { netbeuinetBEUIEntry 31 }

    netbeuiFramesRe-SentPerSec OBJECT-TYPE
        SYNTAX Counter
        ACCESS read-only
        STATUS mandatory
        DESCRIPTION
            "Frames Re-Sent/sec is the rate that data frames (packets) are re-sent by the computer.  This counter only counts the frames or packets that carry data."
        ::= { netbeuinetBEUIEntry 32 }

    netbeuiFrameBytesRe-SentPerSec OBJECT-TYPE
        SYNTAX INTEGER
        ACCESS read-only
        STATUS mandatory
        DESCRIPTION
            "Frame Bytes Re-Sent/sec is the rate that data bytes are re-sent by the computer.  This counter only counts the bytes in frames that carry data."
        ::= { netbeuinetBEUIEntry 33 }

    netbeuiFramesRejectedPerSec OBJECT-TYPE
        SYNTAX Counter
        ACCESS read-only
        STATUS mandatory
        DESCRIPTION
            "Frames Rejected/sec is the rate that data frames are rejected.  This counter only counts the frames (packets) that carry data."
        ::= { netbeuinetBEUIEntry 34 }

    netbeuiFrameBytesRejectedPerSec OBJECT-TYPE
        SYNTAX INTEGER
        ACCESS read-only
        STATUS mandatory
        DESCRIPTION
            "Frame Bytes Rejected/sec is the rate that data bytes are rejected.  This counter only counts the bytes in data frames (packets) that carry data."
        ::= { netbeuinetBEUIEntry 35 }

    netbeuiExpirationsResponse OBJECT-TYPE
        SYNTAX INTEGER
        ACCESS read-only
        STATUS mandatory
        DESCRIPTION
            "Expirations Response is the count of T1 timer expirations."
        ::= { netbeuinetBEUIEntry 36 }

    netbeuiExpirationsAck OBJECT-TYPE
        SYNTAX INTEGER
        ACCESS read-only
        STATUS mandatory
        DESCRIPTION
            "Expirations Ack is the count of T2 timer expirations"
        ::= { netbeuinetBEUIEntry 37 }

    netbeuiWindowSendMaximum OBJECT-TYPE
        SYNTAX INTEGER
        ACCESS read-only
        STATUS mandatory
        DESCRIPTION
            "Window Send Maximum is the maximum number of bytes of data that will be sent before waiting for an acknowledgment from the remote computer."
        ::= { netbeuinetBEUIEntry 38 }

    netbeuiWindowSendAverage OBJECT-TYPE
        SYNTAX INTEGER
        ACCESS read-only
        STATUS mandatory
        DESCRIPTION
            "Window Send Average is the running average number of data bytes that were sent before waiting for an acknowledgment from the remote computer."
        ::= { netbeuinetBEUIEntry 39 }

    netbeuiPiggybackAckQueuedPerSec OBJECT-TYPE
        SYNTAX Counter
        ACCESS read-only
        STATUS mandatory
        DESCRIPTION
            "Piggyback Ack Queued/sec is the rate that piggybacked acknowledgments are queued. Piggyback acknowledgments are acknowledgments to received packets that are to be included in the next outgoing packet to the remote computer."
        ::= { netbeuinetBEUIEntry 40 }

    netbeuiPiggybackAckTimeouts OBJECT-TYPE
        SYNTAX INTEGER
        ACCESS read-only
        STATUS mandatory
        DESCRIPTION
            "Piggyback Ack Timeouts is the number of times that a piggyback acknowledgment could not be sent because there was no outgoing packet to the remote on which to piggyback.  A piggyback ack is an acknowledgment to a received packet that is sent along in an outgoing data packet to the remote computer.  If no outgoing packet is sent within the timeout period, then an ack packet is sent and this counter is incremented."
        ::= { netbeuinetBEUIEntry 41 }

    -- nBT Connection MIB

    nbtconnnBT-ConnectionTable OBJECT-TYPE
        SYNTAX SEQUENCE OF nbtconnnBT-ConnectionEntry
        ACCESS not-accessible
        STATUS mandatory
        DESCRIPTION
            "A table containing performance information for instances of 'nBT-Connection' objects."
        ::= { performance 13 }

    nbtconnnBT-ConnectionEntry OBJECT-TYPE
        SYNTAX nbtconnnBT-ConnectionEntry
        ACCESS not-accessible
        STATUS mandatory
        DESCRIPTION
            "Performance information for one particular instance of 'nBT-Connection' object."
        INDEX { nbtconnnBT-ConnectionIndex }
        ::= { nbtconnnBT-ConnectionTable 1 }

    nbtconnnBT-ConnectionEntry ::=
        SEQUENCE {
            nbtconnnBT-ConnectionIndex INTEGER,
            nbtconnnBT-ConnectionInstance DisplayString,
            nbtconnBytesReceivedPerSec INTEGER,
            nbtconnBytesSentPerSec INTEGER,
            nbtconnBytesTotalPerSec INTEGER
        }

    nbtconnnBT-ConnectionIndex OBJECT-TYPE
        SYNTAX INTEGER
        ACCESS read-only
        STATUS mandatory
        DESCRIPTION
            "Index."
        ::= { nbtconnnBT-ConnectionEntry 1 }

    nbtconnnBT-ConnectionInstance OBJECT-TYPE
        SYNTAX DisplayString
        ACCESS read-only
        STATUS mandatory
        DESCRIPTION
            "Instance name."
        ::= { nbtconnnBT-ConnectionEntry 2 }

    nbtconnBytesReceivedPerSec OBJECT-TYPE
        SYNTAX INTEGER
        ACCESS read-only
        STATUS mandatory
        DESCRIPTION
            "Bytes Received/sec is the rate that bytes are received by the local computer over an NBT connection to some remote computer.  All the bytes received by the local computer over the particular NBT connection are counted."
        ::= { nbtconnnBT-ConnectionEntry 3 }

    nbtconnBytesSentPerSec OBJECT-TYPE
        SYNTAX INTEGER
        ACCESS read-only
        STATUS mandatory
        DESCRIPTION
            "Bytes Sent/sec is the rate that bytes are sent by the local computer over an NBT connection to some remote computer.  All the bytes sent by the local computer over the particular NBT connection are counted."
        ::= { nbtconnnBT-ConnectionEntry 4 }

    nbtconnBytesTotalPerSec OBJECT-TYPE
        SYNTAX INTEGER
        ACCESS read-only
        STATUS mandatory
        DESCRIPTION
            "Total Bytes/sec is the rate that bytes are sent or received by the local computer over an NBT connection to some remote computer.  All the bytes sent or received by the local computer over the particular NBT connection are counted."
        ::= { nbtconnnBT-ConnectionEntry 5 }

    -- nWLink IPX MIB

    nwlinkipxnWLink-IPXTable OBJECT-TYPE
        SYNTAX SEQUENCE OF nwlinkipxnWLink-IPXEntry
        ACCESS not-accessible
        STATUS mandatory
        DESCRIPTION
            "A table containing performance information for instances of 'nWLink-IPX' objects."
        ::= { performance 14 }

    nwlinkipxnWLink-IPXEntry OBJECT-TYPE
        SYNTAX nwlinkipxnWLink-IPXEntry
        ACCESS not-accessible
        STATUS mandatory
        DESCRIPTION
            "Performance information for one particular instance of 'nWLink-IPX' object."
        INDEX { nwlinkipxnWLink-IPXIndex }
        ::= { nwlinkipxnWLink-IPXTable 1 }

    nwlinkipxnWLink-IPXEntry ::=
        SEQUENCE {
            nwlinkipxnWLink-IPXIndex INTEGER,
            nwlinkipxnWLink-IPXInstance DisplayString,
            nwlinkipxDatagramsPerSec Counter,
            nwlinkipxDatagramBytesPerSec INTEGER,
            nwlinkipxPacketsPerSec Counter,
            nwlinkipxFramesPerSec Counter,
            nwlinkipxFrameBytesPerSec INTEGER,
            nwlinkipxBytesTotalPerSec INTEGER,
            nwlinkipxConnectionsOpen INTEGER,
            nwlinkipxConnectionsNoRetries INTEGER,
            nwlinkipxConnectionsWithRetries INTEGER,
            nwlinkipxDisconnectsLocal INTEGER,
            nwlinkipxDisconnectsRemote INTEGER,
            nwlinkipxFailuresLink INTEGER,
            nwlinkipxFailuresAdapter INTEGER,
            nwlinkipxConnectionSessionTimeouts INTEGER,
            nwlinkipxConnectionsCanceled INTEGER,
            nwlinkipxFailuresResourceRemote INTEGER,
            nwlinkipxFailuresResourceLocal INTEGER,
            nwlinkipxFailuresNotFound INTEGER,
            nwlinkipxFailuresNoListen INTEGER,
            nwlinkipxDatagramsSentPerSec Counter,
            nwlinkipxDatagramBytesSentPerSec INTEGER,
            nwlinkipxDatagramsReceivedPerSec Counter,
            nwlinkipxDatagramBytesReceivedPerSec INTEGER,
            nwlinkipxPacketsSentPerSec Counter,
            nwlinkipxPacketsReceivedPerSec Counter,
            nwlinkipxFramesSentPerSec Counter,
            nwlinkipxFrameBytesSentPerSec INTEGER,
            nwlinkipxFramesReceivedPerSec Counter,
            nwlinkipxFrameBytesReceivedPerSec INTEGER,
            nwlinkipxFramesRe-SentPerSec Counter,
            nwlinkipxFrameBytesRe-SentPerSec INTEGER,
            nwlinkipxFramesRejectedPerSec Counter,
            nwlinkipxFrameBytesRejectedPerSec INTEGER,
            nwlinkipxExpirationsResponse INTEGER,
            nwlinkipxExpirationsAck INTEGER,
            nwlinkipxWindowSendMaximum INTEGER,
            nwlinkipxWindowSendAverage INTEGER,
            nwlinkipxPiggybackAckQueuedPerSec Counter,
            nwlinkipxPiggybackAckTimeouts INTEGER
        }

    nwlinkipxnWLink-IPXIndex OBJECT-TYPE
        SYNTAX INTEGER
        ACCESS read-only
        STATUS mandatory
        DESCRIPTION
            "Index."
        ::= { nwlinkipxnWLink-IPXEntry 1 }

    nwlinkipxnWLink-IPXInstance OBJECT-TYPE
        SYNTAX DisplayString
        ACCESS read-only
        STATUS mandatory
        DESCRIPTION
            "Instance name."
        ::= { nwlinkipxnWLink-IPXEntry 2 }

    nwlinkipxDatagramsPerSec OBJECT-TYPE
        SYNTAX Counter
        ACCESS read-only
        STATUS mandatory
        DESCRIPTION
            "Datagrams/sec is the rate that datagrams are processed by the computer.  This counter displays the sum of datagrams sent and datagrams received.  A datagram is a connectionless packet whose delivery to a remote is not guaranteed."
        ::= { nwlinkipxnWLink-IPXEntry 3 }

    nwlinkipxDatagramBytesPerSec OBJECT-TYPE
        SYNTAX INTEGER
        ACCESS read-only
        STATUS mandatory
        DESCRIPTION
            "Datagram Bytes/sec is the rate that datagram bytes are processed by the computer.  This counter is the sum of datagram bytes that are sent as well as received.  A datagram is a connectionless packet whose delivery to a remote is not guaranteed."
        ::= { nwlinkipxnWLink-IPXEntry 4 }

    nwlinkipxPacketsPerSec OBJECT-TYPE
        SYNTAX Counter
        ACCESS read-only
        STATUS mandatory
        DESCRIPTION
            "Packets/sec is the rate that packets are processed by the computer.  This count is the sum of Packets Sent and Packets Received per second.  This counter includes all packets processed: control as well as data packets."
        ::= { nwlinkipxnWLink-IPXEntry 5 }

    nwlinkipxFramesPerSec OBJECT-TYPE
        SYNTAX Counter
        ACCESS read-only
        STATUS mandatory
        DESCRIPTION
            "Frames/sec is the rate that data frames (or packets) are processed by the computer.  This counter is the sum of data frames sent and data frames received.  This counter only counts those frames (packets) that carry data."
        ::= { nwlinkipxnWLink-IPXEntry 6 }

    nwlinkipxFrameBytesPerSec OBJECT-TYPE
        SYNTAX INTEGER
        ACCESS read-only
        STATUS mandatory
        DESCRIPTION
            "Frame Bytes/sec is the rate that data bytes are processed by the computer.  This counter is the sum of data frame bytes sent and received.  This counter only counts the byte in frames (packets) that carry data."
        ::= { nwlinkipxnWLink-IPXEntry 7 }

    nwlinkipxBytesTotalPerSec OBJECT-TYPE
        SYNTAX INTEGER
        ACCESS read-only
        STATUS mandatory
        DESCRIPTION
            "Bytes Total/sec is the sum of Frame Bytes/sec and Datagram Bytes/sec.  This is the total rate of bytes sent to or received from the network by the protocol, but only counts the bytes in frames (i.e., packets) which carry data."
        ::= { nwlinkipxnWLink-IPXEntry 8 }

    nwlinkipxConnectionsOpen OBJECT-TYPE
        SYNTAX INTEGER
        ACCESS read-only
        STATUS mandatory
        DESCRIPTION
            "Connections Open is the number of connections currently open for this protocol.  This counter shows the current count only and does not accumulate over time."
        ::= { nwlinkipxnWLink-IPXEntry 9 }

    nwlinkipxConnectionsNoRetries OBJECT-TYPE
        SYNTAX INTEGER
        ACCESS read-only
        STATUS mandatory
        DESCRIPTION
            "Connections No Retries is the total count of connections that were successfully made on the first try.  This number is an accumulator and shows a running total."
        ::= { nwlinkipxnWLink-IPXEntry 10 }

    nwlinkipxConnectionsWithRetries OBJECT-TYPE
        SYNTAX INTEGER
        ACCESS read-only
        STATUS mandatory
        DESCRIPTION
            "Connections With Retries is the total count of connections that were made after retrying the attempt.  A retry occurs when the first connection attempt failed.  This number is an accumulator and shows a running total."
        ::= { nwlinkipxnWLink-IPXEntry 11 }

    nwlinkipxDisconnectsLocal OBJECT-TYPE
        SYNTAX INTEGER
        ACCESS read-only
        STATUS mandatory
        DESCRIPTION
            "Disconnects Local is the number of session disconnections that were initiated by the local computer.  This number is an accumulator and shows a running total."
        ::= { nwlinkipxnWLink-IPXEntry 12 }

    nwlinkipxDisconnectsRemote OBJECT-TYPE
        SYNTAX INTEGER
        ACCESS read-only
        STATUS mandatory
        DESCRIPTION
            "Disconnects Remote is the number of session disconnections that were initiated by the remote computer.  This number is an accumulator and shows a running total."
        ::= { nwlinkipxnWLink-IPXEntry 13 }

    nwlinkipxFailuresLink OBJECT-TYPE
        SYNTAX INTEGER
        ACCESS read-only
        STATUS mandatory
        DESCRIPTION
            "Failures Link is the number of connections that were dropped due to a link failure.  This number is an accumulator and shows a running total."
        ::= { nwlinkipxnWLink-IPXEntry 14 }

    nwlinkipxFailuresAdapter OBJECT-TYPE
        SYNTAX INTEGER
        ACCESS read-only
        STATUS mandatory
        DESCRIPTION
            "Failures Adapter is the number of connections that were dropped due to an adapter failure.  This number is an accumulator and shows a running total."
        ::= { nwlinkipxnWLink-IPXEntry 15 }

    nwlinkipxConnectionSessionTimeouts OBJECT-TYPE
        SYNTAX INTEGER
        ACCESS read-only
        STATUS mandatory
        DESCRIPTION
            "Connection Session Timeouts is the number of connections that were dropped due to a session timeout.  This number is an accumulator and shows a running total."
        ::= { nwlinkipxnWLink-IPXEntry 16 }

    nwlinkipxConnectionsCanceled OBJECT-TYPE
        SYNTAX INTEGER
        ACCESS read-only
        STATUS mandatory
        DESCRIPTION
            "Connections Canceled is the number of connections that were canceled.  This number is an accumulator and shows a running total."
        ::= { nwlinkipxnWLink-IPXEntry 17 }

    nwlinkipxFailuresResourceRemote OBJECT-TYPE
        SYNTAX INTEGER
        ACCESS read-only
        STATUS mandatory
        DESCRIPTION
            "Failures Resource Remote is the number of connections that failed because of resource problems or shortages on the remote computer.  This number is an accumulator and shows a running total."
        ::= { nwlinkipxnWLink-IPXEntry 18 }

    nwlinkipxFailuresResourceLocal OBJECT-TYPE
        SYNTAX INTEGER
        ACCESS read-only
        STATUS mandatory
        DESCRIPTION
            "Failures Resource Local is the number of connections that failed because of resource problems or shortages on the local computer.  This number is an accumulator and shows a running total."
        ::= { nwlinkipxnWLink-IPXEntry 19 }

    nwlinkipxFailuresNotFound OBJECT-TYPE
        SYNTAX INTEGER
        ACCESS read-only
        STATUS mandatory
        DESCRIPTION
            "Failures Not Found is the number of connection attempts that failed because the remote computer could not be found.  This number is an accumulator and shows a running total."
        ::= { nwlinkipxnWLink-IPXEntry 20 }

    nwlinkipxFailuresNoListen OBJECT-TYPE
        SYNTAX INTEGER
        ACCESS read-only
        STATUS mandatory
        DESCRIPTION
            "Failures No Listen is the number of connections that were rejected because the remote computer was not listening for connection requests."
        ::= { nwlinkipxnWLink-IPXEntry 21 }

    nwlinkipxDatagramsSentPerSec OBJECT-TYPE
        SYNTAX Counter
        ACCESS read-only
        STATUS mandatory
        DESCRIPTION
            "Datagrams Sent/sec is the rate that datagrams are sent from the computer.  A datagram is a connectionless packet whose delivery to a remote computer is not guaranteed."
        ::= { nwlinkipxnWLink-IPXEntry 22 }

    nwlinkipxDatagramBytesSentPerSec OBJECT-TYPE
        SYNTAX INTEGER
        ACCESS read-only
        STATUS mandatory
        DESCRIPTION
            "Datagram Bytes Sent/sec is the rate that datagram bytes are sent from the computer.  A datagram is a connectionless packet whose delivery to a remote computer is not guaranteed."
        ::= { nwlinkipxnWLink-IPXEntry 23 }

    nwlinkipxDatagramsReceivedPerSec OBJECT-TYPE
        SYNTAX Counter
        ACCESS read-only
        STATUS mandatory
        DESCRIPTION
            "Datagrams Received/sec is the rate that datagrams are received by the computer.  A datagram is a connectionless packet whose delivery to a remote computer is not guaranteed."
        ::= { nwlinkipxnWLink-IPXEntry 24 }

    nwlinkipxDatagramBytesReceivedPerSec OBJECT-TYPE
        SYNTAX INTEGER
        ACCESS read-only
        STATUS mandatory
        DESCRIPTION
            "Datagram Bytes Received/sec is the rate that datagram bytes are received by the computer.  A datagram is a connectionless packet whose delivery to a remote computer is not guaranteed."
        ::= { nwlinkipxnWLink-IPXEntry 25 }

    nwlinkipxPacketsSentPerSec OBJECT-TYPE
        SYNTAX Counter
        ACCESS read-only
        STATUS mandatory
        DESCRIPTION
            "Packets Sent/sec is the rate that packets are sent by the computer.  This counter counts all packets sent by the computer, i.e. control as well as data packets."
        ::= { nwlinkipxnWLink-IPXEntry 26 }

    nwlinkipxPacketsReceivedPerSec OBJECT-TYPE
        SYNTAX Counter
        ACCESS read-only
        STATUS mandatory
        DESCRIPTION
            "Packets Received/sec is the rate that packets are received by the computer.  This counter counts all packets processed: control as well as data packets."
        ::= { nwlinkipxnWLink-IPXEntry 27 }

    nwlinkipxFramesSentPerSec OBJECT-TYPE
        SYNTAX Counter
        ACCESS read-only
        STATUS mandatory
        DESCRIPTION
            "Frames Sent/sec is the rate that data frames are sent by the computer.  This counter only counts the frames (packets) that carry data."
        ::= { nwlinkipxnWLink-IPXEntry 28 }

    nwlinkipxFrameBytesSentPerSec OBJECT-TYPE
        SYNTAX INTEGER
        ACCESS read-only
        STATUS mandatory
        DESCRIPTION
            "Frame Bytes Sent/sec is the rate that data bytes are sent by the computer.  This counter only counts the bytes in frames (packets) that carry data."
        ::= { nwlinkipxnWLink-IPXEntry 29 }

    nwlinkipxFramesReceivedPerSec OBJECT-TYPE
        SYNTAX Counter
        ACCESS read-only
        STATUS mandatory
        DESCRIPTION
            "Frames Received/sec is the rate that data frames are received by the computer.  This counter only counts the frames (packets) that carry data."
        ::= { nwlinkipxnWLink-IPXEntry 30 }

    nwlinkipxFrameBytesReceivedPerSec OBJECT-TYPE
        SYNTAX INTEGER
        ACCESS read-only
        STATUS mandatory
        DESCRIPTION
            "Frame Bytes Received/sec is the rate that data bytes are received by the computer.  This counter only counts the frames (packets) that carry data."
        ::= { nwlinkipxnWLink-IPXEntry 31 }

    nwlinkipxFramesRe-SentPerSec OBJECT-TYPE
        SYNTAX Counter
        ACCESS read-only
        STATUS mandatory
        DESCRIPTION
            "Frames Re-Sent/sec is the rate that data frames (packets) are re-sent by the computer.  This counter only counts the frames or packets that carry data."
        ::= { nwlinkipxnWLink-IPXEntry 32 }

    nwlinkipxFrameBytesRe-SentPerSec OBJECT-TYPE
        SYNTAX INTEGER
        ACCESS read-only
        STATUS mandatory
        DESCRIPTION
            "Frame Bytes Re-Sent/sec is the rate that data bytes are re-sent by the computer.  This counter only counts the bytes in frames that carry data."
        ::= { nwlinkipxnWLink-IPXEntry 33 }

    nwlinkipxFramesRejectedPerSec OBJECT-TYPE
        SYNTAX Counter
        ACCESS read-only
        STATUS mandatory
        DESCRIPTION
            "Frames Rejected/sec is the rate that data frames are rejected.  This counter only counts the frames (packets) that carry data."
        ::= { nwlinkipxnWLink-IPXEntry 34 }

    nwlinkipxFrameBytesRejectedPerSec OBJECT-TYPE
        SYNTAX INTEGER
        ACCESS read-only
        STATUS mandatory
        DESCRIPTION
            "Frame Bytes Rejected/sec is the rate that data bytes are rejected.  This counter only counts the bytes in data frames (packets) that carry data."
        ::= { nwlinkipxnWLink-IPXEntry 35 }

    nwlinkipxExpirationsResponse OBJECT-TYPE
        SYNTAX INTEGER
        ACCESS read-only
        STATUS mandatory
        DESCRIPTION
            "Expirations Response is the count of T1 timer expirations."
        ::= { nwlinkipxnWLink-IPXEntry 36 }

    nwlinkipxExpirationsAck OBJECT-TYPE
        SYNTAX INTEGER
        ACCESS read-only
        STATUS mandatory
        DESCRIPTION
            "Expirations Ack is the count of T2 timer expirations"
        ::= { nwlinkipxnWLink-IPXEntry 37 }

    nwlinkipxWindowSendMaximum OBJECT-TYPE
        SYNTAX INTEGER
        ACCESS read-only
        STATUS mandatory
        DESCRIPTION
            "Window Send Maximum is the maximum number of bytes of data that will be sent before waiting for an acknowledgment from the remote computer."
        ::= { nwlinkipxnWLink-IPXEntry 38 }

    nwlinkipxWindowSendAverage OBJECT-TYPE
        SYNTAX INTEGER
        ACCESS read-only
        STATUS mandatory
        DESCRIPTION
            "Window Send Average is the running average number of data bytes that were sent before waiting for an acknowledgment from the remote computer."
        ::= { nwlinkipxnWLink-IPXEntry 39 }

    nwlinkipxPiggybackAckQueuedPerSec OBJECT-TYPE
        SYNTAX Counter
        ACCESS read-only
        STATUS mandatory
        DESCRIPTION
            "Piggyback Ack Queued/sec is the rate that piggybacked acknowledgments are queued. Piggyback acknowledgments are acknowledgments to received packets that are to be included in the next outgoing packet to the remote computer."
        ::= { nwlinkipxnWLink-IPXEntry 40 }

    nwlinkipxPiggybackAckTimeouts OBJECT-TYPE
        SYNTAX INTEGER
        ACCESS read-only
        STATUS mandatory
        DESCRIPTION
            "Piggyback Ack Timeouts is the number of times that a piggyback acknowledgment could not be sent because there was no outgoing packet to the remote on which to piggyback.  A piggyback ack is an acknowledgment to a received packet that is sent along in an outgoing data packet to the remote computer.  If no outgoing packet is sent within the timeout period, then an ack packet is sent and this counter is incremented."
        ::= { nwlinkipxnWLink-IPXEntry 41 }

    -- nWLink SPX MIB

    nwlinkspxnWLink-SPXTable OBJECT-TYPE
        SYNTAX SEQUENCE OF nwlinkspxnWLink-SPXEntry
        ACCESS not-accessible
        STATUS mandatory
        DESCRIPTION
            "A table containing performance information for instances of 'nWLink-SPX' objects."
        ::= { performance 15 }

    nwlinkspxnWLink-SPXEntry OBJECT-TYPE
        SYNTAX nwlinkspxnWLink-SPXEntry
        ACCESS not-accessible
        STATUS mandatory
        DESCRIPTION
            "Performance information for one particular instance of 'nWLink-SPX' object."
        INDEX { nwlinkspxnWLink-SPXIndex }
        ::= { nwlinkspxnWLink-SPXTable 1 }

    nwlinkspxnWLink-SPXEntry ::=
        SEQUENCE {
            nwlinkspxnWLink-SPXIndex INTEGER,
            nwlinkspxnWLink-SPXInstance DisplayString,
            nwlinkspxDatagramsPerSec Counter,
            nwlinkspxDatagramBytesPerSec INTEGER,
            nwlinkspxPacketsPerSec Counter,
            nwlinkspxFramesPerSec Counter,
            nwlinkspxFrameBytesPerSec INTEGER,
            nwlinkspxBytesTotalPerSec INTEGER,
            nwlinkspxConnectionsOpen INTEGER,
            nwlinkspxConnectionsNoRetries INTEGER,
            nwlinkspxConnectionsWithRetries INTEGER,
            nwlinkspxDisconnectsLocal INTEGER,
            nwlinkspxDisconnectsRemote INTEGER,
            nwlinkspxFailuresLink INTEGER,
            nwlinkspxFailuresAdapter INTEGER,
            nwlinkspxConnectionSessionTimeouts INTEGER,
            nwlinkspxConnectionsCanceled INTEGER,
            nwlinkspxFailuresResourceRemote INTEGER,
            nwlinkspxFailuresResourceLocal INTEGER,
            nwlinkspxFailuresNotFound INTEGER,
            nwlinkspxFailuresNoListen INTEGER,
            nwlinkspxDatagramsSentPerSec Counter,
            nwlinkspxDatagramBytesSentPerSec INTEGER,
            nwlinkspxDatagramsReceivedPerSec Counter,
            nwlinkspxDatagramBytesReceivedPerSec INTEGER,
            nwlinkspxPacketsSentPerSec Counter,
            nwlinkspxPacketsReceivedPerSec Counter,
            nwlinkspxFramesSentPerSec Counter,
            nwlinkspxFrameBytesSentPerSec INTEGER,
            nwlinkspxFramesReceivedPerSec Counter,
            nwlinkspxFrameBytesReceivedPerSec INTEGER,
            nwlinkspxFramesRe-SentPerSec Counter,
            nwlinkspxFrameBytesRe-SentPerSec INTEGER,
            nwlinkspxFramesRejectedPerSec Counter,
            nwlinkspxFrameBytesRejectedPerSec INTEGER,
            nwlinkspxExpirationsResponse INTEGER,
            nwlinkspxExpirationsAck INTEGER,
            nwlinkspxWindowSendMaximum INTEGER,
            nwlinkspxWindowSendAverage INTEGER,
            nwlinkspxPiggybackAckQueuedPerSec Counter,
            nwlinkspxPiggybackAckTimeouts INTEGER
        }

    nwlinkspxnWLink-SPXIndex OBJECT-TYPE
        SYNTAX INTEGER
        ACCESS read-only
        STATUS mandatory
        DESCRIPTION
            "Index."
        ::= { nwlinkspxnWLink-SPXEntry 1 }

    nwlinkspxnWLink-SPXInstance OBJECT-TYPE
        SYNTAX DisplayString
        ACCESS read-only
        STATUS mandatory
        DESCRIPTION
            "Instance name."
        ::= { nwlinkspxnWLink-SPXEntry 2 }

    nwlinkspxDatagramsPerSec OBJECT-TYPE
        SYNTAX Counter
        ACCESS read-only
        STATUS mandatory
        DESCRIPTION
            "Datagrams/sec is the rate that datagrams are processed by the computer.  This counter displays the sum of datagrams sent and datagrams received.  A datagram is a connectionless packet whose delivery to a remote is not guaranteed."
        ::= { nwlinkspxnWLink-SPXEntry 3 }

    nwlinkspxDatagramBytesPerSec OBJECT-TYPE
        SYNTAX INTEGER
        ACCESS read-only
        STATUS mandatory
        DESCRIPTION
            "Datagram Bytes/sec is the rate that datagram bytes are processed by the computer.  This counter is the sum of datagram bytes that are sent as well as received.  A datagram is a connectionless packet whose delivery to a remote is not guaranteed."
        ::= { nwlinkspxnWLink-SPXEntry 4 }

    nwlinkspxPacketsPerSec OBJECT-TYPE
        SYNTAX Counter
        ACCESS read-only
        STATUS mandatory
        DESCRIPTION
            "Packets/sec is the rate that packets are processed by the computer.  This count is the sum of Packets Sent and Packets Received per second.  This counter includes all packets processed: control as well as data packets."
        ::= { nwlinkspxnWLink-SPXEntry 5 }

    nwlinkspxFramesPerSec OBJECT-TYPE
        SYNTAX Counter
        ACCESS read-only
        STATUS mandatory
        DESCRIPTION
            "Frames/sec is the rate that data frames (or packets) are processed by the computer.  This counter is the sum of data frames sent and data frames received.  This counter only counts those frames (packets) that carry data."
        ::= { nwlinkspxnWLink-SPXEntry 6 }

    nwlinkspxFrameBytesPerSec OBJECT-TYPE
        SYNTAX INTEGER
        ACCESS read-only
        STATUS mandatory
        DESCRIPTION
            "Frame Bytes/sec is the rate that data bytes are processed by the computer.  This counter is the sum of data frame bytes sent and received.  This counter only counts the byte in frames (packets) that carry data."
        ::= { nwlinkspxnWLink-SPXEntry 7 }

    nwlinkspxBytesTotalPerSec OBJECT-TYPE
        SYNTAX INTEGER
        ACCESS read-only
        STATUS mandatory
        DESCRIPTION
            "Bytes Total/sec is the sum of Frame Bytes/sec and Datagram Bytes/sec.  This is the total rate of bytes sent to or received from the network by the protocol, but only counts the bytes in frames (i.e., packets) which carry data."
        ::= { nwlinkspxnWLink-SPXEntry 8 }

    nwlinkspxConnectionsOpen OBJECT-TYPE
        SYNTAX INTEGER
        ACCESS read-only
        STATUS mandatory
        DESCRIPTION
            "Connections Open is the number of connections currently open for this protocol.  This counter shows the current count only and does not accumulate over time."
        ::= { nwlinkspxnWLink-SPXEntry 9 }

    nwlinkspxConnectionsNoRetries OBJECT-TYPE
        SYNTAX INTEGER
        ACCESS read-only
        STATUS mandatory
        DESCRIPTION
            "Connections No Retries is the total count of connections that were successfully made on the first try.  This number is an accumulator and shows a running total."
        ::= { nwlinkspxnWLink-SPXEntry 10 }

    nwlinkspxConnectionsWithRetries OBJECT-TYPE
        SYNTAX INTEGER
        ACCESS read-only
        STATUS mandatory
        DESCRIPTION
            "Connections With Retries is the total count of connections that were made after retrying the attempt.  A retry occurs when the first connection attempt failed.  This number is an accumulator and shows a running total."
        ::= { nwlinkspxnWLink-SPXEntry 11 }

    nwlinkspxDisconnectsLocal OBJECT-TYPE
        SYNTAX INTEGER
        ACCESS read-only
        STATUS mandatory
        DESCRIPTION
            "Disconnects Local is the number of session disconnections that were initiated by the local computer.  This number is an accumulator and shows a running total."
        ::= { nwlinkspxnWLink-SPXEntry 12 }

    nwlinkspxDisconnectsRemote OBJECT-TYPE
        SYNTAX INTEGER
        ACCESS read-only
        STATUS mandatory
        DESCRIPTION
            "Disconnects Remote is the number of session disconnections that were initiated by the remote computer.  This number is an accumulator and shows a running total."
        ::= { nwlinkspxnWLink-SPXEntry 13 }

    nwlinkspxFailuresLink OBJECT-TYPE
        SYNTAX INTEGER
        ACCESS read-only
        STATUS mandatory
        DESCRIPTION
            "Failures Link is the number of connections that were dropped due to a link failure.  This number is an accumulator and shows a running total."
        ::= { nwlinkspxnWLink-SPXEntry 14 }

    nwlinkspxFailuresAdapter OBJECT-TYPE
        SYNTAX INTEGER
        ACCESS read-only
        STATUS mandatory
        DESCRIPTION
            "Failures Adapter is the number of connections that were dropped due to an adapter failure.  This number is an accumulator and shows a running total."
        ::= { nwlinkspxnWLink-SPXEntry 15 }

    nwlinkspxConnectionSessionTimeouts OBJECT-TYPE
        SYNTAX INTEGER
        ACCESS read-only
        STATUS mandatory
        DESCRIPTION
            "Connection Session Timeouts is the number of connections that were dropped due to a session timeout.  This number is an accumulator and shows a running total."
        ::= { nwlinkspxnWLink-SPXEntry 16 }

    nwlinkspxConnectionsCanceled OBJECT-TYPE
        SYNTAX INTEGER
        ACCESS read-only
        STATUS mandatory
        DESCRIPTION
            "Connections Canceled is the number of connections that were canceled.  This number is an accumulator and shows a running total."
        ::= { nwlinkspxnWLink-SPXEntry 17 }

    nwlinkspxFailuresResourceRemote OBJECT-TYPE
        SYNTAX INTEGER
        ACCESS read-only
        STATUS mandatory
        DESCRIPTION
            "Failures Resource Remote is the number of connections that failed because of resource problems or shortages on the remote computer.  This number is an accumulator and shows a running total."
        ::= { nwlinkspxnWLink-SPXEntry 18 }

    nwlinkspxFailuresResourceLocal OBJECT-TYPE
        SYNTAX INTEGER
        ACCESS read-only
        STATUS mandatory
        DESCRIPTION
            "Failures Resource Local is the number of connections that failed because of resource problems or shortages on the local computer.  This number is an accumulator and shows a running total."
        ::= { nwlinkspxnWLink-SPXEntry 19 }

    nwlinkspxFailuresNotFound OBJECT-TYPE
        SYNTAX INTEGER
        ACCESS read-only
        STATUS mandatory
        DESCRIPTION
            "Failures Not Found is the number of connection attempts that failed because the remote computer could not be found.  This number is an accumulator and shows a running total."
        ::= { nwlinkspxnWLink-SPXEntry 20 }

    nwlinkspxFailuresNoListen OBJECT-TYPE
        SYNTAX INTEGER
        ACCESS read-only
        STATUS mandatory
        DESCRIPTION
            "Failures No Listen is the number of connections that were rejected because the remote computer was not listening for connection requests."
        ::= { nwlinkspxnWLink-SPXEntry 21 }

    nwlinkspxDatagramsSentPerSec OBJECT-TYPE
        SYNTAX Counter
        ACCESS read-only
        STATUS mandatory
        DESCRIPTION
            "Datagrams Sent/sec is the rate that datagrams are sent from the computer.  A datagram is a connectionless packet whose delivery to a remote computer is not guaranteed."
        ::= { nwlinkspxnWLink-SPXEntry 22 }

    nwlinkspxDatagramBytesSentPerSec OBJECT-TYPE
        SYNTAX INTEGER
        ACCESS read-only
        STATUS mandatory
        DESCRIPTION
            "Datagram Bytes Sent/sec is the rate that datagram bytes are sent from the computer.  A datagram is a connectionless packet whose delivery to a remote computer is not guaranteed."
        ::= { nwlinkspxnWLink-SPXEntry 23 }

    nwlinkspxDatagramsReceivedPerSec OBJECT-TYPE
        SYNTAX Counter
        ACCESS read-only
        STATUS mandatory
        DESCRIPTION
            "Datagrams Received/sec is the rate that datagrams are received by the computer.  A datagram is a connectionless packet whose delivery to a remote computer is not guaranteed."
        ::= { nwlinkspxnWLink-SPXEntry 24 }

    nwlinkspxDatagramBytesReceivedPerSec OBJECT-TYPE
        SYNTAX INTEGER
        ACCESS read-only
        STATUS mandatory
        DESCRIPTION
            "Datagram Bytes Received/sec is the rate that datagram bytes are received by the computer.  A datagram is a connectionless packet whose delivery to a remote computer is not guaranteed."
        ::= { nwlinkspxnWLink-SPXEntry 25 }

    nwlinkspxPacketsSentPerSec OBJECT-TYPE
        SYNTAX Counter
        ACCESS read-only
        STATUS mandatory
        DESCRIPTION
            "Packets Sent/sec is the rate that packets are sent by the computer.  This counter counts all packets sent by the computer, i.e. control as well as data packets."
        ::= { nwlinkspxnWLink-SPXEntry 26 }

    nwlinkspxPacketsReceivedPerSec OBJECT-TYPE
        SYNTAX Counter
        ACCESS read-only
        STATUS mandatory
        DESCRIPTION
            "Packets Received/sec is the rate that packets are received by the computer.  This counter counts all packets processed: control as well as data packets."
        ::= { nwlinkspxnWLink-SPXEntry 27 }

    nwlinkspxFramesSentPerSec OBJECT-TYPE
        SYNTAX Counter
        ACCESS read-only
        STATUS mandatory
        DESCRIPTION
            "Frames Sent/sec is the rate that data frames are sent by the computer.  This counter only counts the frames (packets) that carry data."
        ::= { nwlinkspxnWLink-SPXEntry 28 }

    nwlinkspxFrameBytesSentPerSec OBJECT-TYPE
        SYNTAX INTEGER
        ACCESS read-only
        STATUS mandatory
        DESCRIPTION
            "Frame Bytes Sent/sec is the rate that data bytes are sent by the computer.  This counter only counts the bytes in frames (packets) that carry data."
        ::= { nwlinkspxnWLink-SPXEntry 29 }

    nwlinkspxFramesReceivedPerSec OBJECT-TYPE
        SYNTAX Counter
        ACCESS read-only
        STATUS mandatory
        DESCRIPTION
            "Frames Received/sec is the rate that data frames are received by the computer.  This counter only counts the frames (packets) that carry data."
        ::= { nwlinkspxnWLink-SPXEntry 30 }

    nwlinkspxFrameBytesReceivedPerSec OBJECT-TYPE
        SYNTAX INTEGER
        ACCESS read-only
        STATUS mandatory
        DESCRIPTION
            "Frame Bytes Received/sec is the rate that data bytes are received by the computer.  This counter only counts the frames (packets) that carry data."
        ::= { nwlinkspxnWLink-SPXEntry 31 }

    nwlinkspxFramesRe-SentPerSec OBJECT-TYPE
        SYNTAX Counter
        ACCESS read-only
        STATUS mandatory
        DESCRIPTION
            "Frames Re-Sent/sec is the rate that data frames (packets) are re-sent by the computer.  This counter only counts the frames or packets that carry data."
        ::= { nwlinkspxnWLink-SPXEntry 32 }

    nwlinkspxFrameBytesRe-SentPerSec OBJECT-TYPE
        SYNTAX INTEGER
        ACCESS read-only
        STATUS mandatory
        DESCRIPTION
            "Frame Bytes Re-Sent/sec is the rate that data bytes are re-sent by the computer.  This counter only counts the bytes in frames that carry data."
        ::= { nwlinkspxnWLink-SPXEntry 33 }

    nwlinkspxFramesRejectedPerSec OBJECT-TYPE
        SYNTAX Counter
        ACCESS read-only
        STATUS mandatory
        DESCRIPTION
            "Frames Rejected/sec is the rate that data frames are rejected.  This counter only counts the frames (packets) that carry data."
        ::= { nwlinkspxnWLink-SPXEntry 34 }

    nwlinkspxFrameBytesRejectedPerSec OBJECT-TYPE
        SYNTAX INTEGER
        ACCESS read-only
        STATUS mandatory
        DESCRIPTION
            "Frame Bytes Rejected/sec is the rate that data bytes are rejected.  This counter only counts the bytes in data frames (packets) that carry data."
        ::= { nwlinkspxnWLink-SPXEntry 35 }

    nwlinkspxExpirationsResponse OBJECT-TYPE
        SYNTAX INTEGER
        ACCESS read-only
        STATUS mandatory
        DESCRIPTION
            "Expirations Response is the count of T1 timer expirations."
        ::= { nwlinkspxnWLink-SPXEntry 36 }

    nwlinkspxExpirationsAck OBJECT-TYPE
        SYNTAX INTEGER
        ACCESS read-only
        STATUS mandatory
        DESCRIPTION
            "Expirations Ack is the count of T2 timer expirations"
        ::= { nwlinkspxnWLink-SPXEntry 37 }

    nwlinkspxWindowSendMaximum OBJECT-TYPE
        SYNTAX INTEGER
        ACCESS read-only
        STATUS mandatory
        DESCRIPTION
            "Window Send Maximum is the maximum number of bytes of data that will be sent before waiting for an acknowledgment from the remote computer."
        ::= { nwlinkspxnWLink-SPXEntry 38 }

    nwlinkspxWindowSendAverage OBJECT-TYPE
        SYNTAX INTEGER
        ACCESS read-only
        STATUS mandatory
        DESCRIPTION
            "Window Send Average is the running average number of data bytes that were sent before waiting for an acknowledgment from the remote computer."
        ::= { nwlinkspxnWLink-SPXEntry 39 }

    nwlinkspxPiggybackAckQueuedPerSec OBJECT-TYPE
        SYNTAX Counter
        ACCESS read-only
        STATUS mandatory
        DESCRIPTION
            "Piggyback Ack Queued/sec is the rate that piggybacked acknowledgments are queued. Piggyback acknowledgments are acknowledgments to received packets that are to be included in the next outgoing packet to the remote computer."
        ::= { nwlinkspxnWLink-SPXEntry 40 }

    nwlinkspxPiggybackAckTimeouts OBJECT-TYPE
        SYNTAX INTEGER
        ACCESS read-only
        STATUS mandatory
        DESCRIPTION
            "Piggyback Ack Timeouts is the number of times that a piggyback acknowledgment could not be sent because there was no outgoing packet to the remote on which to piggyback.  A piggyback ack is an acknowledgment to a received packet that is sent along in an outgoing data packet to the remote computer.  If no outgoing packet is sent within the timeout period, then an ack packet is sent and this counter is incremented."
        ::= { nwlinkspxnWLink-SPXEntry 41 }

    -- rAS Total MIB

    rAS-Total OBJECT IDENTIFIER ::= { performance 16 }

    rastotalBytesTransmitted OBJECT-TYPE
        SYNTAX INTEGER
        ACCESS read-only
        STATUS mandatory
        DESCRIPTION
            "The number of bytes transmitted total for this connection."
        ::= { rAS-Total 1 }

    rastotalBytesReceived OBJECT-TYPE
        SYNTAX INTEGER
        ACCESS read-only
        STATUS mandatory
        DESCRIPTION
            "The number of bytes received total for this connection."
        ::= { rAS-Total 2 }

    rastotalFramesTransmitted OBJECT-TYPE
        SYNTAX INTEGER
        ACCESS read-only
        STATUS mandatory
        DESCRIPTION
            "The number of data frames transmitted total for this connection."
        ::= { rAS-Total 3 }

    rastotalFramesReceived OBJECT-TYPE
        SYNTAX INTEGER
        ACCESS read-only
        STATUS mandatory
        DESCRIPTION
            "The number of data frames received total for this connection."
        ::= { rAS-Total 4 }

    rastotalPercentCompressionOut OBJECT-TYPE
        SYNTAX INTEGER
        ACCESS read-only
        STATUS mandatory
        DESCRIPTION
            "The compression ratio for bytes being transmitted."
        ::= { rAS-Total 5 }

    rastotalPercentCompressionIn OBJECT-TYPE
        SYNTAX INTEGER
        ACCESS read-only
        STATUS mandatory
        DESCRIPTION
            "The compression ratio for bytes being received."
        ::= { rAS-Total 6 }

    rastotalCRCErrors OBJECT-TYPE
        SYNTAX INTEGER
        ACCESS read-only
        STATUS mandatory
        DESCRIPTION
            "The total number of CRC Errors for this connection.  CRC Errors occur when the frame received contains erroneous data."
        ::= { rAS-Total 7 }

    rastotalTimeoutErrors OBJECT-TYPE
        SYNTAX INTEGER
        ACCESS read-only
        STATUS mandatory
        DESCRIPTION
            "The total number of Timeout Errors for this connection.  Timeout Errors occur when an expected is not received in time."
        ::= { rAS-Total 8 }

    rastotalSerialOverrunErrors OBJECT-TYPE
        SYNTAX INTEGER
        ACCESS read-only
        STATUS mandatory
        DESCRIPTION
            "The total number of Serial Overrun Errors for this connection.  Serial Overrun Errors occur when the hardware cannot handle the rate at which data is received."
        ::= { rAS-Total 9 }

    rastotalAlignmentErrors OBJECT-TYPE
        SYNTAX INTEGER
        ACCESS read-only
        STATUS mandatory
        DESCRIPTION
            "The total number of Alignment Errors for this connection.  Alignment Errors occur when a byte received is different from the byte expected."
        ::= { rAS-Total 10 }

    rastotalBufferOverrunErrors OBJECT-TYPE
        SYNTAX INTEGER
        ACCESS read-only
        STATUS mandatory
        DESCRIPTION
            "The total number of Buffer Overrun Errors for this connection.  Buffer Overrun Errors when the software cannot handle the rate at which data is received."
        ::= { rAS-Total 11 }

    rastotalTotalErrors OBJECT-TYPE
        SYNTAX INTEGER
        ACCESS read-only
        STATUS mandatory
        DESCRIPTION
            "The total number of CRC, Timeout, Serial Overrun, Alignment, and Buffer Overrun Errors for this connection."
        ::= { rAS-Total 12 }

    rastotalBytesTransmittedPerSec OBJECT-TYPE
        SYNTAX Counter
        ACCESS read-only
        STATUS mandatory
        DESCRIPTION
            "The number of bytes transmitted per second."
        ::= { rAS-Total 13 }

    rastotalBytesReceivedPerSec OBJECT-TYPE
        SYNTAX Counter
        ACCESS read-only
        STATUS mandatory
        DESCRIPTION
            "The number of bytes received per second."
        ::= { rAS-Total 14 }

    rastotalFramesTransmittedPerSec OBJECT-TYPE
        SYNTAX Counter
        ACCESS read-only
        STATUS mandatory
        DESCRIPTION
            "The number of frames transmitted per second."
        ::= { rAS-Total 15 }

    rastotalFramesReceivedPerSec OBJECT-TYPE
        SYNTAX Counter
        ACCESS read-only
        STATUS mandatory
        DESCRIPTION
            "The number of frames received per second."
        ::= { rAS-Total 16 }

    rastotalTotalErrorsPerSec OBJECT-TYPE
        SYNTAX Counter
        ACCESS read-only
        STATUS mandatory
        DESCRIPTION
            "The total number of CRC, Timeout, Serial Overrun, Alignment, and Buffer Overrun Errors per second."
        ::= { rAS-Total 17 }

    rastotalTotalConnections OBJECT-TYPE
        SYNTAX INTEGER
        ACCESS read-only
        STATUS mandatory
        DESCRIPTION
            "The total number of Remote Access connections."
        ::= { rAS-Total 18 }

    -- server MIB

    server OBJECT IDENTIFIER ::= { performance 17 }

    serverBytesTotalPerSec OBJECT-TYPE
        SYNTAX INTEGER
        ACCESS read-only
        STATUS mandatory
        DESCRIPTION
            "The number of bytes the server has sent to and received from the network.  This value provides an overall indication of how busy the server is."
        ::= { server 1 }

    serverBytesReceivedPerSec OBJECT-TYPE
        SYNTAX INTEGER
        ACCESS read-only
        STATUS mandatory
        DESCRIPTION
            "The number of bytes the server has received from the network.  Indicates how busy the server is."
        ::= { server 2 }

    serverBytesTransmittedPerSec OBJECT-TYPE
        SYNTAX INTEGER
        ACCESS read-only
        STATUS mandatory
        DESCRIPTION
            "The number of bytes the server has sent on the network.  Indicates how busy the server is."
        ::= { server 3 }

    serverSessionsTimedOut OBJECT-TYPE
        SYNTAX INTEGER
        ACCESS read-only
        STATUS mandatory
        DESCRIPTION
            "The number of sessions that have been closed due to their idle time exceeding the autodisconnect parameter for the server.  Shows whether the autodisconnect setting is helping to conserve resources."
        ::= { server 4 }

    serverSessionsErroredOut OBJECT-TYPE
        SYNTAX INTEGER
        ACCESS read-only
        STATUS mandatory
        DESCRIPTION
            "The number of sessions that have been closed due to unexpected error conditions.  Indicates how frequently network problems are causing dropped sessions on the server."
        ::= { server 5 }

    serverSessionsLoggedOff OBJECT-TYPE
        SYNTAX INTEGER
        ACCESS read-only
        STATUS mandatory
        DESCRIPTION
            "The number of sessions that have terminated normally. Useful in interpreting the Sessions Times Out and Sessions Errored Out statistics--allows percentage calculations."
        ::= { server 6 }

    serverSessionsForcedOff OBJECT-TYPE
        SYNTAX INTEGER
        ACCESS read-only
        STATUS mandatory
        DESCRIPTION
            "The number of sessions that have been forced to logoff.  Can indicate how many sessions were forced to logoff due to logon time constraints."
        ::= { server 7 }

    serverErrorsLogon OBJECT-TYPE
        SYNTAX INTEGER
        ACCESS read-only
        STATUS mandatory
        DESCRIPTION
            "The number of failed logon attempts to the server.  Can indicate whether password guessing programs are being used to crack the security on the server."
        ::= { server 8 }

    serverErrorsAccessPermissions OBJECT-TYPE
        SYNTAX INTEGER
        ACCESS read-only
        STATUS mandatory
        DESCRIPTION
            "The number of times opens on behalf of clients have failed with STATUS_ACCESS_DENIED.  Can indicate whether somebody is randomly attempting to access files in hopes of getting at something that was not properly protected."
        ::= { server 9 }

    serverErrorsGrantedAccess OBJECT-TYPE
        SYNTAX INTEGER
        ACCESS read-only
        STATUS mandatory
        DESCRIPTION
            "The number of times accesses to files opened successfully were denied.  Can indicate attempts to access files without proper access authorization."
        ::= { server 10 }

    serverErrorsSystem OBJECT-TYPE
        SYNTAX INTEGER
        ACCESS read-only
        STATUS mandatory
        DESCRIPTION
            "The number of times an internal Server Error was detected.  Unexpected errors usually indicate a problem with the Server."
        ::= { server 11 }

    serverBlockingRequestsRejected OBJECT-TYPE
        SYNTAX Counter
        ACCESS read-only
        STATUS mandatory
        DESCRIPTION
            "The number of times the server has rejected blocking SMBs due to insufficient count of free work items. Indicates whether the maxworkitem or minfreeworkitems server parameters may need tuning."
        ::= { server 12 }

    serverWorkItemShortages OBJECT-TYPE
        SYNTAX Counter
        ACCESS read-only
        STATUS mandatory
        DESCRIPTION
            "The number of times STATUS_DATA_NOT_ACCEPTED was returned at receive indication time.  This occurs when no work item is available or can be allocated to service the incoming request.  Indicates whether the initworkitems or maxworkitems parameters may need tuning."
        ::= { server 13 }

    serverFilesOpenedTotal OBJECT-TYPE
        SYNTAX INTEGER
        ACCESS read-only
        STATUS mandatory
        DESCRIPTION
            "The number of successful open attempts performed by the server of behalf of clients.  Useful in determining the amount of file I/O, determining overhead for path-based operations, determining the effectiveness of oplocks."
        ::= { server 14 }

    serverFilesOpen OBJECT-TYPE
        SYNTAX INTEGER
        ACCESS read-only
        STATUS mandatory
        DESCRIPTION
            "The number of files currently opened in the server.  Indicates current server activity."
        ::= { server 15 }

    serverServerSessions OBJECT-TYPE
        SYNTAX INTEGER
        ACCESS read-only
        STATUS mandatory
        DESCRIPTION
            "The number of sessions currently active in the server.  Indicates current server activity."
        ::= { server 16 }

    serverFileDirectorySearches OBJECT-TYPE
        SYNTAX INTEGER
        ACCESS read-only
        STATUS mandatory
        DESCRIPTION
            "The number of searches for files currently active in the server.  Indicates current server activity."
        ::= { server 17 }

    serverPoolNonpagedBytes OBJECT-TYPE
        SYNTAX INTEGER
        ACCESS read-only
        STATUS mandatory
        DESCRIPTION
            "The number of bytes of non-pageable computer memory the server is currently using.  Can help in determining good values for the maxnonpagedmemoryusage parameter."
        ::= { server 18 }

    serverPoolNonpagedFailures OBJECT-TYPE
        SYNTAX Counter
        ACCESS read-only
        STATUS mandatory
        DESCRIPTION
            "The number of times allocations from nonpaged pool have failed.  Indicates that the computer's physical memory is too small."
        ::= { server 19 }

    serverPoolNonpagedPeak OBJECT-TYPE
        SYNTAX INTEGER
        ACCESS read-only
        STATUS mandatory
        DESCRIPTION
            "The maximum number of bytes of nonpaged pool the server has had in use at any one point.  Indicates how much physical memory the computer should have."
        ::= { server 20 }

    serverPoolPagedBytes OBJECT-TYPE
        SYNTAX INTEGER
        ACCESS read-only
        STATUS mandatory
        DESCRIPTION
            "The number of bytes of pageable computer memory the server is currently using.  Can help in determining good values for the maxpagedmemoryusage parameter."
        ::= { server 21 }

    serverPoolPagedFailures OBJECT-TYPE
        SYNTAX INTEGER
        ACCESS read-only
        STATUS mandatory
        DESCRIPTION
            "The number of times allocations from paged pool have failed.  Indicates that the computer's physical memory of pagefile are too small."
        ::= { server 22 }

    serverPoolPagedPeak OBJECT-TYPE
        SYNTAX INTEGER
        ACCESS read-only
        STATUS mandatory
        DESCRIPTION
            "The maximum number of bytes of paged pool the server has had allocated.  Indicates the proper sizes of the Page File(s) and physical memory."
        ::= { server 23 }

    serverContextBlocksQueuedPerSec OBJECT-TYPE
        SYNTAX Counter
        ACCESS read-only
        STATUS mandatory
        DESCRIPTION
            "Context Blocks Queued per second is the rate that work context blocks had to be placed on the server's FSP queue to await server action."
        ::= { server 24 }

    serverLogonPerSec OBJECT-TYPE
        SYNTAX Counter
        ACCESS read-only
        STATUS mandatory
        DESCRIPTION
            "Logon/sec is the rate of all server logons"
        ::= { server 25 }

    serverLogonTotal OBJECT-TYPE
        SYNTAX INTEGER
        ACCESS read-only
        STATUS mandatory
        DESCRIPTION
            "Logon Total includes all interactive logons, network logons, service logons, successful logon, and failed logons since the machine is last rebooted."
        ::= { server 26 }

    -- server Work Queues MIB

    srvrqueuesserver-Work-QueuesTable OBJECT-TYPE
        SYNTAX SEQUENCE OF srvrqueuesserver-Work-QueuesEntry
        ACCESS not-accessible
        STATUS mandatory
        DESCRIPTION
            "A table containing performance information for instances of 'server-Work-Queues' objects."
        ::= { performance 18 }

    srvrqueuesserver-Work-QueuesEntry OBJECT-TYPE
        SYNTAX srvrqueuesserver-Work-QueuesEntry
        ACCESS not-accessible
        STATUS mandatory
        DESCRIPTION
            "Performance information for one particular instance of 'server-Work-Queues' object."
        INDEX { srvrqueuesserver-Work-QueuesIndex }
        ::= { srvrqueuesserver-Work-QueuesTable 1 }

    srvrqueuesserver-Work-QueuesEntry ::=
        SEQUENCE {
            srvrqueuesserver-Work-QueuesIndex INTEGER,
            srvrqueuesserver-Work-QueuesInstance DisplayString,
            srvrqueuesQueueLength INTEGER,
            srvrqueuesActiveThreads INTEGER,
            srvrqueuesAvailableThreads INTEGER,
            srvrqueuesAvailableWorkItems INTEGER,
            srvrqueuesBorrowedWorkItems INTEGER,
            srvrqueuesWorkItemShortages INTEGER,
            srvrqueuesCurrentClients INTEGER,
            srvrqueuesBytesReceivedPerSec INTEGER,
            srvrqueuesBytesSentPerSec INTEGER,
            srvrqueuesBytesTransferredPerSec INTEGER,
            srvrqueuesReadOperationsPerSec INTEGER,
            srvrqueuesReadBytesPerSec INTEGER,
            srvrqueuesWriteOperationsPerSec INTEGER,
            srvrqueuesWriteBytesPerSec INTEGER,
            srvrqueuesTotalBytesPerSec INTEGER,
            srvrqueuesTotalOperationsPerSec INTEGER,
            srvrqueuesContextBlocksQueuedPerSec Counter
        }

    srvrqueuesserver-Work-QueuesIndex OBJECT-TYPE
        SYNTAX INTEGER
        ACCESS read-only
        STATUS mandatory
        DESCRIPTION
            "Index."
        ::= { srvrqueuesserver-Work-QueuesEntry 1 }

    srvrqueuesserver-Work-QueuesInstance OBJECT-TYPE
        SYNTAX DisplayString
        ACCESS read-only
        STATUS mandatory
        DESCRIPTION
            "Instance name."
        ::= { srvrqueuesserver-Work-QueuesEntry 2 }

    srvrqueuesQueueLength OBJECT-TYPE
        SYNTAX INTEGER
        ACCESS read-only
        STATUS mandatory
        DESCRIPTION
            "Queue Length is the current length of the server work queue for this CPU. A sustained queue length greater than four may indicate processor congestion. This is an instantaneous count, not an average over time."
        ::= { srvrqueuesserver-Work-QueuesEntry 3 }

    srvrqueuesActiveThreads OBJECT-TYPE
        SYNTAX INTEGER
        ACCESS read-only
        STATUS mandatory
        DESCRIPTION
            "Active Threads is the number of threads currently working on a request from the server client for this CPU. The system keeps this number as low as possible to minimize unnecessary context switching. This is an instantaneous count for the CPU, not an average over time."
        ::= { srvrqueuesserver-Work-QueuesEntry 4 }

    srvrqueuesAvailableThreads OBJECT-TYPE
        SYNTAX INTEGER
        ACCESS read-only
        STATUS mandatory
        DESCRIPTION
            "Available Threads is the number of server threads on this CPU not currently working on requests from a client.  The server dynamically adjusts the number of threads to maximize server performance."
        ::= { srvrqueuesserver-Work-QueuesEntry 5 }

    srvrqueuesAvailableWorkItems OBJECT-TYPE
        SYNTAX INTEGER
        ACCESS read-only
        STATUS mandatory
        DESCRIPTION
            "Every request from a client is represented in the server as a 'work item,' and the server maintains a pool of available work items per CPU to speed processing.  This is the instantaneous number of available work items for this CPU.  A sustained near-zero value indicates the need to increase the MinFreeWorkItems registry value for the Server service.  This value will always be 0 in the Blocking Queue instance."
        ::= { srvrqueuesserver-Work-QueuesEntry 6 }

    srvrqueuesBorrowedWorkItems OBJECT-TYPE
        SYNTAX INTEGER
        ACCESS read-only
        STATUS mandatory
        DESCRIPTION
            "Every request from a client is represented in the server as a 'work item,' and the server maintains a pool of available work items per CPU to speed processing. When a CPU runs out of work items, it borrows a free work item from another CPU.  An increasing value of this running counter may indicate the need to increase the 'MaxWorkItems' or 'MinFreeWorkItems' registry values for the Server service.  This value will always be 0 in the Blocking Queue instance."
        ::= { srvrqueuesserver-Work-QueuesEntry 7 }

    srvrqueuesWorkItemShortages OBJECT-TYPE
        SYNTAX INTEGER
        ACCESS read-only
        STATUS mandatory
        DESCRIPTION
            "Every request from a client is represented in the server as a 'work item,' and the server maintains a pool of available work items per CPU to speed processing. A sustained value greater than zero indicates the need to increase the 'MaxWorkItems' registry value for the Server service.  This value will always be 0 in the Blocking Queue instance."
        ::= { srvrqueuesserver-Work-QueuesEntry 8 }

    srvrqueuesCurrentClients OBJECT-TYPE
        SYNTAX INTEGER
        ACCESS read-only
        STATUS mandatory
        DESCRIPTION
            "Current Clients is the instantaneous count of the clients being serviced by this CPU.  The server actively balances the client load across all of the CPU's in the system.  This value will always be 0 in the Blocking Queue instance."
        ::= { srvrqueuesserver-Work-QueuesEntry 9 }

    srvrqueuesBytesReceivedPerSec OBJECT-TYPE
        SYNTAX INTEGER
        ACCESS read-only
        STATUS mandatory
        DESCRIPTION
            "The rate at which the Server is receiving bytes from the network clients on this CPU. This value is a measure of how busy the Server is."
        ::= { srvrqueuesserver-Work-QueuesEntry 10 }

    srvrqueuesBytesSentPerSec OBJECT-TYPE
        SYNTAX INTEGER
        ACCESS read-only
        STATUS mandatory
        DESCRIPTION
            "The rate at which the Server is sending bytes to the network clients on this CPU. This value is a measure of how busy the Server is."
        ::= { srvrqueuesserver-Work-QueuesEntry 11 }

    srvrqueuesBytesTransferredPerSec OBJECT-TYPE
        SYNTAX INTEGER
        ACCESS read-only
        STATUS mandatory
        DESCRIPTION
            "The rate at which the Server is sending and receiving bytes with the network clients on this CPU. This value is a measure of how busy the Server is."
        ::= { srvrqueuesserver-Work-QueuesEntry 12 }

    srvrqueuesReadOperationsPerSec OBJECT-TYPE
        SYNTAX INTEGER
        ACCESS read-only
        STATUS mandatory
        DESCRIPTION
            "Read Operations/sec is the rate the server is performing file read operations for the clients on this CPU. This value is a measure of how busy the Server is. This value will always be 0 in the Blocking Queue instance."
        ::= { srvrqueuesserver-Work-QueuesEntry 13 }

    srvrqueuesReadBytesPerSec OBJECT-TYPE
        SYNTAX INTEGER
        ACCESS read-only
        STATUS mandatory
        DESCRIPTION
            "Read Bytes/sec is the rate the server is reading data from files for the clients on this CPU. This value is a measure of how busy the Server is."
        ::= { srvrqueuesserver-Work-QueuesEntry 14 }

    srvrqueuesWriteOperationsPerSec OBJECT-TYPE
        SYNTAX INTEGER
        ACCESS read-only
        STATUS mandatory
        DESCRIPTION
            "Write Operations/sec is the rate the server is performing file write operations for the clients on this CPU.  This value is a measure of how busy the Server is.  This value will always be 0 in the Blocking Queue instance."
        ::= { srvrqueuesserver-Work-QueuesEntry 15 }

    srvrqueuesWriteBytesPerSec OBJECT-TYPE
        SYNTAX INTEGER
        ACCESS read-only
        STATUS mandatory
        DESCRIPTION
            "Write Bytes/sec is the rate the server is writing data to files for the clients on this CPU. This value is a measure of how busy the Server is."
        ::= { srvrqueuesserver-Work-QueuesEntry 16 }

    srvrqueuesTotalBytesPerSec OBJECT-TYPE
        SYNTAX INTEGER
        ACCESS read-only
        STATUS mandatory
        DESCRIPTION
            "Total Bytes/sec is the rate the Server is reading and writing data to and from the files for the clients on this CPU. This value is a measure of how busy the Server is."
        ::= { srvrqueuesserver-Work-QueuesEntry 17 }

    srvrqueuesTotalOperationsPerSec OBJECT-TYPE
        SYNTAX INTEGER
        ACCESS read-only
        STATUS mandatory
        DESCRIPTION
            "Total Operations/sec is the rate the Server is performing file read and file write operations for the cliens on this CPU.  This value is a measure of how busy the Server is.  This value will always be 0 in the Blocking Queue instance."
        ::= { srvrqueuesserver-Work-QueuesEntry 18 }

    srvrqueuesContextBlocksQueuedPerSec OBJECT-TYPE
        SYNTAX Counter
        ACCESS read-only
        STATUS mandatory
        DESCRIPTION
            "Context Blocks Queued per second is the rate that work context blocks had to be placed on the server's FSP queue to await server action."
        ::= { srvrqueuesserver-Work-QueuesEntry 19 }

    -- cache MIB

    cache OBJECT IDENTIFIER ::= { performance 19 }

    cacheDataMapsPerSec OBJECT-TYPE
        SYNTAX Counter
        ACCESS read-only
        STATUS mandatory
        DESCRIPTION
            "Data Maps/sec is the frequency that a file system such as NTFS or HPFS maps a page of a file into the Cache to read the page."
        ::= { cache 1 }

    cacheSyncDataMapsPerSec OBJECT-TYPE
        SYNTAX Counter
        ACCESS read-only
        STATUS mandatory
        DESCRIPTION
            "Sync Data Maps/sec counts the frequency that a file system such as NTFS or HPFS maps a page of a file into the Cache to read the page, and wishes to wait for the Cache to retrieve the page if it is not in main memory."
        ::= { cache 2 }

    cacheAsyncDataMapsPerSec OBJECT-TYPE
        SYNTAX Counter
        ACCESS read-only
        STATUS mandatory
        DESCRIPTION
            "Async Data Maps/sec is the frequency that an application using a file system such as NTFS or HPFS to map a page of a file into the Cache to read the page, and does not wish to wait for the Cache to retrieve the page if it is not in main memory."
        ::= { cache 3 }

    cacheDataMapHitsPercent OBJECT-TYPE
        SYNTAX INTEGER
        ACCESS read-only
        STATUS mandatory
        DESCRIPTION
            "Data Map Hits is the percentage of Data Maps in the Cache that could be resolved without having to retrieve a page from the disk, i.e. the page was already in physical memory."
        ::= { cache 4 }

    cacheDataMapPinsPerSec OBJECT-TYPE
        SYNTAX INTEGER
        ACCESS read-only
        STATUS mandatory
        DESCRIPTION
            "Data Map Pins/sec is the frequency of Data Maps in the Cache that resulted in pinning a page in main memory, an action usually preparatory to writing to the file on disk.  While pinned, a page's physical address in main memory and virtual address in the Cache will not be altered."
        ::= { cache 6 }

    cachePinReadsPerSec OBJECT-TYPE
        SYNTAX Counter
        ACCESS read-only
        STATUS mandatory
        DESCRIPTION
            "Pin Reads/sec is the frequency of reading data into the Cache preparatory to writing the data back to disk.  Pages read in this fashion are pinned in memory at the completion of the read.  While pinned, a page's physical address in the Cache will not be altered."
        ::= { cache 8 }

    cacheSyncPinReadsPerSec OBJECT-TYPE
        SYNTAX Counter
        ACCESS read-only
        STATUS mandatory
        DESCRIPTION
            "Sync Pin Reads/sec is the frequency of reading data into the Cache preparatory to writing the data back to disk.  Pages read in this fashion are pinned in memory at the completion of the read.  The file system will not regain control until the page is pinned in the Cache, in particular if the disk must be accessed to retrieve the page.  While pinned, a page's physical address in the Cache will not be altered."
        ::= { cache 9 }

    cacheAsyncPinReadsPerSec OBJECT-TYPE
        SYNTAX Counter
        ACCESS read-only
        STATUS mandatory
        DESCRIPTION
            "Async Pin Reads/sec is the frequency of reading data into the Cache preparatory to writing the data back to disk.   Pages read in this fashion are pinned in memory at the completion of the read.  The file system will regain control immediately even if the disk must be accessed to retrieve the page.  While pinned, a page's physical address will not be altered."
        ::= { cache 10 }

    cachePinReadHitsPercent OBJECT-TYPE
        SYNTAX INTEGER
        ACCESS read-only
        STATUS mandatory
        DESCRIPTION
            "Pin Read Hits is the percentage of Cache Pin Read requests that hit the Cache, i.e., did not require a disk read in order to provide access to the page in the Cache.  While pinned, a page's physical address in the Cache will not be altered.  The LAN Redirector uses this method for retrieving Cache information, as does the LAN Server for small transfers.  This is usually the method used by the disk file systems as well."
        ::= { cache 11 }

    cacheCopyReadsPerSec OBJECT-TYPE
        SYNTAX Counter
        ACCESS read-only
        STATUS mandatory
        DESCRIPTION
            "Copy Reads/sec is the frequency of reads from Cache pages that involve a memory copy of the data from the Cache to the application's buffer.  The LAN Redirector uses this method for retrieving Cache information, as does the LAN Server for small transfers.  This is a method used by the disk file systems as well."
        ::= { cache 13 }

    cacheSyncCopyReadsPerSec OBJECT-TYPE
        SYNTAX Counter
        ACCESS read-only
        STATUS mandatory
        DESCRIPTION
            "Sync Copy Reads/sec is the frequency of reads from Cache pages that involve a memory copy of the data from the Cache to the application's buffer.  The file system will not regain control until the copy operation is complete, even if the disk must be accessed to retrieve the page."
        ::= { cache 14 }

    cacheAsyncCopyReadsPerSec OBJECT-TYPE
        SYNTAX Counter
        ACCESS read-only
        STATUS mandatory
        DESCRIPTION
            "Async Copy Reads/sec is the frequency of reads from Cache pages that involve a memory copy of the data from the Cache to the application's buffer.  The application will regain control immediately even if the disk must be accessed to retrieve the page."
        ::= { cache 15 }

    cacheCopyReadHitsPercent OBJECT-TYPE
        SYNTAX INTEGER
        ACCESS read-only
        STATUS mandatory
        DESCRIPTION
            "Copy Read Hits is the percentage of Cache Copy Read requests that hit the Cache, i.e., did not require a disk read in order to provide access to the page in the Cache.  A Copy Read is a file read operation that is satisfied by a memory copy from a Cache page to the application's buffer.  The LAN Redirector uses this method for retrieving Cache information, as does the LAN Server for small transfers.  This is a method used by the disk file systems as well."
        ::= { cache 16 }

    cacheMDLReadsPerSec OBJECT-TYPE
        SYNTAX Counter
        ACCESS read-only
        STATUS mandatory
        DESCRIPTION
            "MDL Reads/sec is the frequency of reads from Cache pages that use a Memory Descriptor List (MDL) to access the data.  The MDL contains the physical address of each page involved in the transfer, and thus can employ a hardware Direct Memory Access (DMA) device to effect the copy.  The LAN Server uses this method for large transfers out of the server."
        ::= { cache 18 }

    cacheSyncMDLReadsPerSec OBJECT-TYPE
        SYNTAX Counter
        ACCESS read-only
        STATUS mandatory
        DESCRIPTION
            "Sync MDL Reads/sec is the frequency of reads from Cache pages that use a Memory Descriptor List (MDL) to access the pages.  The MDL contains the physical address of each page in the transfer, thus permitting Direct Memory Access (DMA) of the pages.  If the accessed page(s) are not in main memory, the caller will wait for the pages to fault in from the disk."
        ::= { cache 19 }

    cacheAsyncMDLReadsPerSec OBJECT-TYPE
        SYNTAX Counter
        ACCESS read-only
        STATUS mandatory
        DESCRIPTION
            "Async MDL Reads/sec is the frequency of reads from Cache pages using a Memory Descriptor List (MDL) to access the pages.  The MDL contains the physical address of each page in the transfer, thus permitting Direct Memory Access (DMA) of the pages.  If the accessed page(s) are not in main memory, the calling application program will not wait for the pages to fault in from disk."
        ::= { cache 20 }

    cacheMDLReadHitsPercent OBJECT-TYPE
        SYNTAX INTEGER
        ACCESS read-only
        STATUS mandatory
        DESCRIPTION
            "MDL Read Hits is the percentage of Cache Memory Descriptor List (MDL) Read requests that hit the Cache, i.e., did not require disk accesses in order to provide memory access to the page(s) in the Cache."
        ::= { cache 21 }

    cacheReadAheadsPerSec OBJECT-TYPE
        SYNTAX Counter
        ACCESS read-only
        STATUS mandatory
        DESCRIPTION
            "Read Aheads/sec is the frequency of Cache reads where the Cache detects sequential access to a file.  The read aheads permit the data to be transferred in larger blocks than those being requested by the application, reducing the overhead per access."
        ::= { cache 23 }

    cacheFastReadsPerSec OBJECT-TYPE
        SYNTAX Counter
        ACCESS read-only
        STATUS mandatory
        DESCRIPTION
            "Fast Reads/sec is the frequency of reads from Cache pages that bypass the installed file system and retrieve the data directly from the Cache.  Normally, file I/O requests invoke the appropriate file system to retrieve data from a file, but this path permits direct retrieval of Cache data without file system involvement if the data is in the Cache.  Even if the data is not in the Cache, one invocation of the file system is avoided."
        ::= { cache 24 }

    cacheSyncFastReadsPerSec OBJECT-TYPE
        SYNTAX Counter
        ACCESS read-only
        STATUS mandatory
        DESCRIPTION
            "Sync Fast Reads/sec is the frequency of reads from Cache pages that bypass the installed file system and retrieve the data directly from the Cache.  Normally, file I/O requests invoke the appropriate file system to retrieve data from a file, but this path permits direct retrieval of Cache data without file system involvement if the data is in the Cache.  Even if the data is not in the Cache, one invocation of the file system is avoided.  If the data is not in the Cache, the request (application program call) will wait until the data has been retrieved from disk."
        ::= { cache 25 }

    cacheAsyncFastReadsPerSec OBJECT-TYPE
        SYNTAX Counter
        ACCESS read-only
        STATUS mandatory
        DESCRIPTION
            "Async Fast Reads/sec is the frequency of reads from Cache pages that bypass the installed file system and retrieve the data directly from the Cache.  Normally, file I/O requests will invoke the appropriate file system to retrieve data from a file, but this path permits direct retrieval of Cache data without file system involvement if the data is in the Cache.  Even if the data is not in the Cache, one invocation of the file system is avoided.  If the data is not in the Cache, the request (application program call) will not wait until the data has been retrieved from disk, but will get control immediately."
        ::= { cache 26 }

    cacheFastReadResourceMissesPerSec OBJECT-TYPE
        SYNTAX Counter
        ACCESS read-only
        STATUS mandatory
        DESCRIPTION
            "Fast Read Resource Misses/sec is the frequency of Cache misses necessitated by the lack of available resources to satisfy the request."
        ::= { cache 27 }

    cacheFastReadNotPossiblesPerSec OBJECT-TYPE
        SYNTAX Counter
        ACCESS read-only
        STATUS mandatory
        DESCRIPTION
            "Fast Read Not Possibles/sec is the frequency of attempts by an Application Program Interface (API) function call to bypass the file system to get at Cache data, that could not be honored without invoking the file system after all."
        ::= { cache 28 }

    cacheLazyWriteFlushesPerSec OBJECT-TYPE
        SYNTAX Counter
        ACCESS read-only
        STATUS mandatory
        DESCRIPTION
            "Lazy Write Flushes/sec is the frequency the Cache's Lazy Write thread has written to disk.  Lazy Writing is the process of updating the disk after the page has been changed in memory, so the application making the change to the file does not have to wait for the disk write to complete before proceeding.  More than one page can be transferred on each write operation."
        ::= { cache 29 }

    cacheLazyWritePagesPerSec OBJECT-TYPE
        SYNTAX Counter
        ACCESS read-only
        STATUS mandatory
        DESCRIPTION
            "Lazy Write Pages/sec is the frequency the Cache's Lazy Write thread has written to disk.  Lazy Writing is the process of updating the disk after the page has been changed in memory, so the application making the change to the file does not have to wait for the disk write to complete before proceeding.  More than one page can be transferred on a single disk write operation."
        ::= { cache 30 }

    cacheDataFlushesPerSec OBJECT-TYPE
        SYNTAX Counter
        ACCESS read-only
        STATUS mandatory
        DESCRIPTION
            "Data Flushes/sec is the frequency the Cache has flushed its contents to disk as the result of a request to flush or to satisfy a write-through file write request.  More than one page can be transferred on each flush operation."
        ::= { cache 31 }

    cacheDataFlushPagesPerSec OBJECT-TYPE
        SYNTAX Counter
        ACCESS read-only
        STATUS mandatory
        DESCRIPTION
            "Data Flush Pages/sec is the number of pages the Cache has flushed to disk as a result of a request to flush or to satisfy a write-through file write request.  More than one page can be transferred on each flush operation."
        ::= { cache 32 }

    -- mSExchangeMTA MIB

    mSExchangeMTA OBJECT IDENTIFIER ::= { performance 20 }

    exchmtaAdjacentMTAAssociations OBJECT-TYPE
        SYNTAX INTEGER
        ACCESS read-only
        STATUS mandatory
        DESCRIPTION
            "Adjacent MTA Associations is the number of open associations this MTA has to other MTAs."
        ::= { mSExchangeMTA 1 }

    exchmtaMessagesPerSec OBJECT-TYPE
        SYNTAX Counter
        ACCESS read-only
        STATUS mandatory
        DESCRIPTION
            "Messages/sec is the rate that messages are processed."
        ::= { mSExchangeMTA 2 }

    exchmtaMessageBytesPerSec OBJECT-TYPE
        SYNTAX Counter
        ACCESS read-only
        STATUS mandatory
        DESCRIPTION
            "Message Bytes/sec is the rate that message bytes are processed."
        ::= { mSExchangeMTA 3 }

    exchmtaFreeElements OBJECT-TYPE
        SYNTAX INTEGER
        ACCESS read-only
        STATUS mandatory
        DESCRIPTION
            "Free Elements is the number of free buffer elements in the MTA pool."
        ::= { mSExchangeMTA 4 }

    exchmtaFreeHeaders OBJECT-TYPE
        SYNTAX INTEGER
        ACCESS read-only
        STATUS mandatory
        DESCRIPTION
            "Free Headers is the number of free buffer headers in the MTA pool."
        ::= { mSExchangeMTA 5 }

    exchmtaAdminConnections OBJECT-TYPE
        SYNTAX INTEGER
        ACCESS read-only
        STATUS mandatory
        DESCRIPTION
            "Admin Connections is the number of Microsoft Exchange Administrator programs connected to this MTA."
        ::= { mSExchangeMTA 6 }

    exchmtaThreadsInUse OBJECT-TYPE
        SYNTAX INTEGER
        ACCESS read-only
        STATUS mandatory
        DESCRIPTION
            "Threads in Use is the number of threads in use by the MTA (does not include RPC threads). This number can be used to determine whether additional processors could be of benefit."
        ::= { mSExchangeMTA 7 }

    exchmtaWorkQueueLength OBJECT-TYPE
        SYNTAX INTEGER
        ACCESS read-only
        STATUS mandatory
        DESCRIPTION
            "Work Queue Length is the number of outstanding messages in the Work Queue, which indicates the number of messages not yet processed to completion by the MTA."
        ::= { mSExchangeMTA 8 }

    exchmtaXAPIGateways OBJECT-TYPE
        SYNTAX INTEGER
        ACCESS read-only
        STATUS mandatory
        DESCRIPTION
            "XAPI Gateways is the number of gateways connected to the MTA using the XAPI MT/OM interface. A single gateway may have multiple XAPI gateway sessions."
        ::= { mSExchangeMTA 9 }

    exchmtaXAPIClients OBJECT-TYPE
        SYNTAX INTEGER
        ACCESS read-only
        STATUS mandatory
        DESCRIPTION
            "XAPI Clients is the number of XAPI clients connected to the MTA using the XAPI MA/OM interface. A single client may have multiple XAPI client sessions."
        ::= { mSExchangeMTA 10 }

    exchmtaDiskFileDeletesPerSec OBJECT-TYPE
        SYNTAX Counter
        ACCESS read-only
        STATUS mandatory
        DESCRIPTION
            "Disk File Deletes/sec is the rate of disk file delete operations."
        ::= { mSExchangeMTA 11 }

    exchmtaDiskFileSyncsPerSec OBJECT-TYPE
        SYNTAX Counter
        ACCESS read-only
        STATUS mandatory
        DESCRIPTION
            "Disk File Syncs/sec is the rate of disk file sync operations."
        ::= { mSExchangeMTA 12 }

    exchmtaDiskFileOpensPerSec OBJECT-TYPE
        SYNTAX Counter
        ACCESS read-only
        STATUS mandatory
        DESCRIPTION
            "Disk File Opens/sec is the rate of disk file open operations."
        ::= { mSExchangeMTA 13 }

    exchmtaDiskFileReadsPerSec OBJECT-TYPE
        SYNTAX Counter
        ACCESS read-only
        STATUS mandatory
        DESCRIPTION
            "Disk File Reads/sec is the rate of disk file read operations."
        ::= { mSExchangeMTA 14 }

    exchmtaDiskFileWritesPerSec OBJECT-TYPE
        SYNTAX Counter
        ACCESS read-only
        STATUS mandatory
        DESCRIPTION
            "Disk File Writes/sec is the rate of disk file write operations."
        ::= { mSExchangeMTA 15 }

    exchmtaExDSReadCallsPerSec OBJECT-TYPE
        SYNTAX Counter
        ACCESS read-only
        STATUS mandatory
        DESCRIPTION
            "ExDS Read Calls/sec is the rate of read calls to the directory service."
        ::= { mSExchangeMTA 16 }

    exchmtaXAPIReceiveBytesPerSec OBJECT-TYPE
        SYNTAX Counter
        ACCESS read-only
        STATUS mandatory
        DESCRIPTION
            "XAPI Receive Bytes/sec is the rate that bytes are received over a XAPI connection."
        ::= { mSExchangeMTA 17 }

    exchmtaXAPITransmitBytesPerSec OBJECT-TYPE
        SYNTAX Counter
        ACCESS read-only
        STATUS mandatory
        DESCRIPTION
            "XAPI Transmit Bytes/sec is the rate that bytes are transmitted over a XAPI connection."
        ::= { mSExchangeMTA 18 }

    exchmtaAdminInterfaceReceiveBytesPerSec OBJECT-TYPE
        SYNTAX Counter
        ACCESS read-only
        STATUS mandatory
        DESCRIPTION
            "Admin Interface Receive Bytes/sec is the rate that bytes are received over an Admin connection."
        ::= { mSExchangeMTA 19 }

    exchmtaAdminInterfaceTransmitBytesPerSec OBJECT-TYPE
        SYNTAX Counter
        ACCESS read-only
        STATUS mandatory
        DESCRIPTION
            "Admin Interface Transmit Bytes/sec is the rate that bytes are transmitted over an Admin connection."
        ::= { mSExchangeMTA 20 }

    exchmtaLANReceiveBytesPerSec OBJECT-TYPE
        SYNTAX Counter
        ACCESS read-only
        STATUS mandatory
        DESCRIPTION
            "LAN Receive Bytes/sec is the rate that bytes are received over a LAN from MTAs."
        ::= { mSExchangeMTA 21 }

    exchmtaLANTransmitBytesPerSec OBJECT-TYPE
        SYNTAX Counter
        ACCESS read-only
        STATUS mandatory
        DESCRIPTION
            "LAN Transmit Bytes/sec is the rate that bytes are transmitted over a LAN to MTAs."
        ::= { mSExchangeMTA 22 }

    exchmtaRASReceiveBytesPerSec OBJECT-TYPE
        SYNTAX Counter
        ACCESS read-only
        STATUS mandatory
        DESCRIPTION
            "RAS Receive Bytes/sec is the rate that bytes are received over a RAS connection."
        ::= { mSExchangeMTA 23 }

    exchmtaRASTransmitBytesPerSec OBJECT-TYPE
        SYNTAX Counter
        ACCESS read-only
        STATUS mandatory
        DESCRIPTION
            "RAS Transmit Bytes/sec is the rate that bytes are transmitted over a RAS connection."
        ::= { mSExchangeMTA 24 }

    exchmtaTCPPerIPReceiveBytesPerSec OBJECT-TYPE
        SYNTAX Counter
        ACCESS read-only
        STATUS mandatory
        DESCRIPTION
            "TCP/IP Receive Bytes/sec is the rate that bytes are received over a TCP/IP connection."
        ::= { mSExchangeMTA 25 }

    exchmtaTCPPerIPTransmitBytesPerSec OBJECT-TYPE
        SYNTAX Counter
        ACCESS read-only
        STATUS mandatory
        DESCRIPTION
            "TCP/IP Transmit Bytes/sec is the rate that bytes are transmitted over a TCP/IP connection."
        ::= { mSExchangeMTA 26 }

    exchmtaTP4ReceiveBytesPerSec OBJECT-TYPE
        SYNTAX Counter
        ACCESS read-only
        STATUS mandatory
        DESCRIPTION
            "TP4 Receive Bytes/sec is the rate that bytes are received over a TP4 connection."
        ::= { mSExchangeMTA 27 }

    exchmtaTP4TransmitBytesPerSec OBJECT-TYPE
        SYNTAX Counter
        ACCESS read-only
        STATUS mandatory
        DESCRIPTION
            "TP4 Transmit Bytes/sec is the rate that bytes are transmitted over a TP4 connection."
        ::= { mSExchangeMTA 28 }

    exchmtaX25ReceiveBytesPerSec OBJECT-TYPE
        SYNTAX Counter
        ACCESS read-only
        STATUS mandatory
        DESCRIPTION
            "X.25 Receive Bytes/sec is the rate that bytes are received over an X.25 connection."
        ::= { mSExchangeMTA 29 }

    exchmtaX25TransmitBytesPerSec OBJECT-TYPE
        SYNTAX Counter
        ACCESS read-only
        STATUS mandatory
        DESCRIPTION
            "X.25 Transmit Bytes/sec is the rate that bytes are transmitted over an X.25 connection."
        ::= { mSExchangeMTA 30 }

    exchmtaDeferredDeliveryMsgs OBJECT-TYPE
        SYNTAX INTEGER
        ACCESS read-only
        STATUS mandatory
        DESCRIPTION
            "Deferred Delivery Msgs is the total number of deferred delivery messages currently stored in the MTA."
        ::= { mSExchangeMTA 31 }

    exchmtaTotalRecipientsQueued OBJECT-TYPE
        SYNTAX INTEGER
        ACCESS read-only
        STATUS mandatory
        DESCRIPTION
            "Total Recipients Queued is the total number of recipients specified in all messages currently stored in the MTA."
        ::= { mSExchangeMTA 32 }

    exchmtaTotalSuccessfulConversions OBJECT-TYPE
        SYNTAX INTEGER
        ACCESS read-only
        STATUS mandatory
        DESCRIPTION
            "Total Successful Conversions is the total number of messages successfully converted from one form to another since MTA initialization."
        ::= { mSExchangeMTA 33 }

    exchmtaTotalFailedConversions OBJECT-TYPE
        SYNTAX INTEGER
        ACCESS read-only
        STATUS mandatory
        DESCRIPTION
            "Total Failed Conversions is the total number of messages which failed to be converted from one form to another since MTA initialization."
        ::= { mSExchangeMTA 34 }

    exchmtaTotalLoopsDetected OBJECT-TYPE
        SYNTAX INTEGER
        ACCESS read-only
        STATUS mandatory
        DESCRIPTION
            "Total Loops Detected is the total number  of messages detected to have looped since MTA initialization."
        ::= { mSExchangeMTA 35 }

    exchmtaInboundMessagesTotal OBJECT-TYPE
        SYNTAX Counter
        ACCESS read-only
        STATUS mandatory
        DESCRIPTION
            "Inbound Messages Total is the total number of messages received since MTA initialization."
        ::= { mSExchangeMTA 36 }

    exchmtaOutboundMessagesTotal OBJECT-TYPE
        SYNTAX Counter
        ACCESS read-only
        STATUS mandatory
        DESCRIPTION
            "Outbound Messages Total is the total number of messages transmitted since MTA initialization."
        ::= { mSExchangeMTA 37 }

    exchmtaInboundBytesTotal OBJECT-TYPE
        SYNTAX Counter
        ACCESS read-only
        STATUS mandatory
        DESCRIPTION
            "Inbound Bytes Total is the total volume of message content received since MTA initialization, measured in kilobytes."
        ::= { mSExchangeMTA 38 }

    exchmtaWorkQueueBytes OBJECT-TYPE
        SYNTAX Counter
        ACCESS read-only
        STATUS mandatory
        DESCRIPTION
            "Work Queue Bytes is the total volume of message content currently stored in the MTA, measured in kilobytes."
        ::= { mSExchangeMTA 39 }

    exchmtaOutboundBytesTotal OBJECT-TYPE
        SYNTAX Counter
        ACCESS read-only
        STATUS mandatory
        DESCRIPTION
            "Outbound Bytes Total is the total volume of message content transmitted since MTA initialization, measured in kilobytes."
        ::= { mSExchangeMTA 40 }

    exchmtaTotalRecipientsInbound OBJECT-TYPE
        SYNTAX Counter
        ACCESS read-only
        STATUS mandatory
        DESCRIPTION
            "Total Recipients Inbound is the total number of recipients specified in all messages received since MTA initialization."
        ::= { mSExchangeMTA 41 }

    exchmtaTotalRecipientsOutbound OBJECT-TYPE
        SYNTAX Counter
        ACCESS read-only
        STATUS mandatory
        DESCRIPTION
            "Total Recipients Outbound is the total number of recipients specified in all messages transmitted since MTA initialization."
        ::= { mSExchangeMTA 42 }

    -- mSExchangeMTA Connections MIB

    exchmtaconnmSExchangeMTA-ConnectionsTable OBJECT-TYPE
        SYNTAX SEQUENCE OF exchmtaconnmSExchangeMTA-ConnectionsEntry
        ACCESS not-accessible
        STATUS mandatory
        DESCRIPTION
            "A table containing performance information for instances of 'mSExchangeMTA-Connections' objects."
        ::= { performance 21 }

    exchmtaconnmSExchangeMTA-ConnectionsEntry OBJECT-TYPE
        SYNTAX exchmtaconnmSExchangeMTA-ConnectionsEntry
        ACCESS not-accessible
        STATUS mandatory
        DESCRIPTION
            "Performance information for one particular instance of 'mSExchangeMTA-Connections' object."
        INDEX { exchmtaconnmSExchangeMTA-ConnectionsIndex }
        ::= { exchmtaconnmSExchangeMTA-ConnectionsTable 1 }

    exchmtaconnmSExchangeMTA-ConnectionsEntry ::=
        SEQUENCE {
            exchmtaconnmSExchangeMTA-ConnectionsIndex INTEGER,
            exchmtaconnmSExchangeMTA-ConnectionsInstance DisplayString,
            exchmtaconnAssociations INTEGER,
            exchmtaconnReceiveBytesPerSec Counter,
            exchmtaconnSendBytesPerSec Counter,
            exchmtaconnReceiveMessagesPerSec Counter,
            exchmtaconnSendMessagesPerSec Counter,
            exchmtaconnQueueLength INTEGER,
            exchmtaconnConnectorIndex INTEGER,
            exchmtaconnInboundRejectedTotal INTEGER,
            exchmtaconnTotalRecipientsQueued INTEGER,
            exchmtaconnOldestMessageQueued TimeTicks,
            exchmtaconnCurrentInboundAssociations INTEGER,
            exchmtaconnCurrentOutboundAssociations INTEGER,
            exchmtaconnCumulativeInboundAssociations INTEGER,
            exchmtaconnCumulativeOutboundAssociations INTEGER,
            exchmtaconnLastInboundAssociation TimeTicks,
            exchmtaconnLastOutboundAssociation TimeTicks,
            exchmtaconnRejectedInboundAssociations INTEGER,
            exchmtaconnFailedOutboundAssociations INTEGER,
            exchmtaconnNextAssociationRetry INTEGER,
            exchmtaconnInboundRejectReason INTEGER,
            exchmtaconnOutboundFailureReason INTEGER,
            exchmtaconnInboundMessagesTotal Counter,
            exchmtaconnOutboundMessagesTotal Counter,
            exchmtaconnInboundBytesTotal Counter,
            exchmtaconnQueuedBytes Counter,
            exchmtaconnOutboundBytesTotal Counter,
            exchmtaconnTotalRecipientsInbound Counter,
            exchmtaconnTotalRecipientsOutbound Counter
        }

    exchmtaconnmSExchangeMTA-ConnectionsIndex OBJECT-TYPE
        SYNTAX INTEGER
        ACCESS read-only
        STATUS mandatory
        DESCRIPTION
            "Index."
        ::= { exchmtaconnmSExchangeMTA-ConnectionsEntry 1 }

    exchmtaconnmSExchangeMTA-ConnectionsInstance OBJECT-TYPE
        SYNTAX DisplayString
        ACCESS read-only
        STATUS mandatory
        DESCRIPTION
            "Instance name."
        ::= { exchmtaconnmSExchangeMTA-ConnectionsEntry 2 }

    exchmtaconnAssociations OBJECT-TYPE
        SYNTAX INTEGER
        ACCESS read-only
        STATUS mandatory
        DESCRIPTION
            "Associations is the number of associations between the MTA and the connected entity. MTAs may open multiple associations if additional transfer throughput is necessary."
        ::= { exchmtaconnmSExchangeMTA-ConnectionsEntry 3 }

    exchmtaconnReceiveBytesPerSec OBJECT-TYPE
        SYNTAX Counter
        ACCESS read-only
        STATUS mandatory
        DESCRIPTION
            "Receive Bytes/sec is the rate that bytes are received from the connected entity."
        ::= { exchmtaconnmSExchangeMTA-ConnectionsEntry 4 }

    exchmtaconnSendBytesPerSec OBJECT-TYPE
        SYNTAX Counter
        ACCESS read-only
        STATUS mandatory
        DESCRIPTION
            "Send Bytes/sec is the rate that bytes are sent to the connected entity."
        ::= { exchmtaconnmSExchangeMTA-ConnectionsEntry 5 }

    exchmtaconnReceiveMessagesPerSec OBJECT-TYPE
        SYNTAX Counter
        ACCESS read-only
        STATUS mandatory
        DESCRIPTION
            "Receive Messages/sec is the rate that messages are received from the connected entity."
        ::= { exchmtaconnmSExchangeMTA-ConnectionsEntry 6 }

    exchmtaconnSendMessagesPerSec OBJECT-TYPE
        SYNTAX Counter
        ACCESS read-only
        STATUS mandatory
        DESCRIPTION
            "Send Messages/sec is the rate that messages are sent to the connected entity."
        ::= { exchmtaconnmSExchangeMTA-ConnectionsEntry 7 }

    exchmtaconnQueueLength OBJECT-TYPE
        SYNTAX INTEGER
        ACCESS read-only
        STATUS mandatory
        DESCRIPTION
            "Queue Length is the number of outstanding messages queued for transfer to the entity."
        ::= { exchmtaconnmSExchangeMTA-ConnectionsEntry 8 }

    exchmtaconnConnectorIndex OBJECT-TYPE
        SYNTAX INTEGER
        ACCESS read-only
        STATUS mandatory
        DESCRIPTION
            "Connector Index is a unique index associated with a connector entity."
        ::= { exchmtaconnmSExchangeMTA-ConnectionsEntry 9 }

    exchmtaconnInboundRejectedTotal OBJECT-TYPE
        SYNTAX INTEGER
        ACCESS read-only
        STATUS mandatory
        DESCRIPTION
            "Inbound Rejected Total is the total number of messages rejected from this entity since MTA initialization."
        ::= { exchmtaconnmSExchangeMTA-ConnectionsEntry 10 }

    exchmtaconnTotalRecipientsQueued OBJECT-TYPE
        SYNTAX INTEGER
        ACCESS read-only
        STATUS mandatory
        DESCRIPTION
            "Total Recipients Queued is the total number of recipients specified in all messages currently stored in this entity's queue."
        ::= { exchmtaconnmSExchangeMTA-ConnectionsEntry 11 }

    exchmtaconnOldestMessageQueued OBJECT-TYPE
        SYNTAX TimeTicks
        ACCESS read-only
        STATUS mandatory
        DESCRIPTION
            "Oldest Message Queued is the time (secs) since the oldest message in this entity's queue was placed in the queue."
        ::= { exchmtaconnmSExchangeMTA-ConnectionsEntry 12 }

    exchmtaconnCurrentInboundAssociations OBJECT-TYPE
        SYNTAX INTEGER
        ACCESS read-only
        STATUS mandatory
        DESCRIPTION
            "Current Inbound Associations is the current number of inbound (remote initiated) associations with the entity."
        ::= { exchmtaconnmSExchangeMTA-ConnectionsEntry 13 }

    exchmtaconnCurrentOutboundAssociations OBJECT-TYPE
        SYNTAX INTEGER
        ACCESS read-only
        STATUS mandatory
        DESCRIPTION
            "Current Outbound Associations is the current number of outbound (locally initiated) associations with the entity."
        ::= { exchmtaconnmSExchangeMTA-ConnectionsEntry 14 }

    exchmtaconnCumulativeInboundAssociations OBJECT-TYPE
        SYNTAX INTEGER
        ACCESS read-only
        STATUS mandatory
        DESCRIPTION
            "Cumulative Inbound Associations is the total number of inbound (remote initiated) associations with the entity, since MTA initialization."
        ::= { exchmtaconnmSExchangeMTA-ConnectionsEntry 15 }

    exchmtaconnCumulativeOutboundAssociations OBJECT-TYPE
        SYNTAX INTEGER
        ACCESS read-only
        STATUS mandatory
        DESCRIPTION
            "Cumulative Outbound Associations is the total number of outbound (locally initiated) associations with the entity, since MTA initialization."
        ::= { exchmtaconnmSExchangeMTA-ConnectionsEntry 16 }

    exchmtaconnLastInboundAssociation OBJECT-TYPE
        SYNTAX TimeTicks
        ACCESS read-only
        STATUS mandatory
        DESCRIPTION
            "Last Inbound Association is the time (secs) since the last time an inbound (remote initiated) association for this entity was active."
        ::= { exchmtaconnmSExchangeMTA-ConnectionsEntry 17 }

    exchmtaconnLastOutboundAssociation OBJECT-TYPE
        SYNTAX TimeTicks
        ACCESS read-only
        STATUS mandatory
        DESCRIPTION
            "Last Outbound Association is the time (secs) since the last time an outbound (locally initiated) association for this entity was active."
        ::= { exchmtaconnmSExchangeMTA-ConnectionsEntry 18 }

    exchmtaconnRejectedInboundAssociations OBJECT-TYPE
        SYNTAX INTEGER
        ACCESS read-only
        STATUS mandatory
        DESCRIPTION
            "Rejected Inbound Associations is the total number of inbound (remote initiated) associations that have been rejected, since MTA initialization."
        ::= { exchmtaconnmSExchangeMTA-ConnectionsEntry 19 }

    exchmtaconnFailedOutboundAssociations OBJECT-TYPE
        SYNTAX INTEGER
        ACCESS read-only
        STATUS mandatory
        DESCRIPTION
            "Failed Outbound Associations is the total number of outbound (locally initiated) associations that have failed, since MTA initialization."
        ::= { exchmtaconnmSExchangeMTA-ConnectionsEntry 20 }

    exchmtaconnNextAssociationRetry OBJECT-TYPE
        SYNTAX INTEGER
        ACCESS read-only
        STATUS mandatory
        DESCRIPTION
            "Next Association Retry is the time (secs since 00:00 1st Jan 1970) when this entity is next scheduled to attempt to open an association."
        ::= { exchmtaconnmSExchangeMTA-ConnectionsEntry 21 }

    exchmtaconnInboundRejectReason OBJECT-TYPE
        SYNTAX INTEGER
        ACCESS read-only
        STATUS mandatory
        DESCRIPTION
            "Inbound Reject Reason is the reject reason code, if any, for the last association rejected from this entity."
        ::= { exchmtaconnmSExchangeMTA-ConnectionsEntry 22 }

    exchmtaconnOutboundFailureReason OBJECT-TYPE
        SYNTAX INTEGER
        ACCESS read-only
        STATUS mandatory
        DESCRIPTION
            "Outbound Failure Reason is the failure reason code, if any, for the last association attempt to this entity."
        ::= { exchmtaconnmSExchangeMTA-ConnectionsEntry 23 }

    exchmtaconnInboundMessagesTotal OBJECT-TYPE
        SYNTAX Counter
        ACCESS read-only
        STATUS mandatory
        DESCRIPTION
            "Inbound Messages Total is the total number of messages received from this entity since MTA initialization."
        ::= { exchmtaconnmSExchangeMTA-ConnectionsEntry 24 }

    exchmtaconnOutboundMessagesTotal OBJECT-TYPE
        SYNTAX Counter
        ACCESS read-only
        STATUS mandatory
        DESCRIPTION
            "Outbound Messages Total is the total number of messages transmitted to this entity since MTA initialization."
        ::= { exchmtaconnmSExchangeMTA-ConnectionsEntry 25 }

    exchmtaconnInboundBytesTotal OBJECT-TYPE
        SYNTAX Counter
        ACCESS read-only
        STATUS mandatory
        DESCRIPTION
            "Inbound Bytes Total is the total volume of message content received from this entity since MTA initialization, measured in kilobytes."
        ::= { exchmtaconnmSExchangeMTA-ConnectionsEntry 26 }

    exchmtaconnQueuedBytes OBJECT-TYPE
        SYNTAX Counter
        ACCESS read-only
        STATUS mandatory
        DESCRIPTION
            "Queued Bytes is the total volume of message content currently stored in this entity's queue, measured in kilobytes."
        ::= { exchmtaconnmSExchangeMTA-ConnectionsEntry 27 }

    exchmtaconnOutboundBytesTotal OBJECT-TYPE
        SYNTAX Counter
        ACCESS read-only
        STATUS mandatory
        DESCRIPTION
            "Outbound Bytes Total is the total volume of message content transmitted to this entity since MTA initialization, measured in kilobytes."
        ::= { exchmtaconnmSExchangeMTA-ConnectionsEntry 28 }

    exchmtaconnTotalRecipientsInbound OBJECT-TYPE
        SYNTAX Counter
        ACCESS read-only
        STATUS mandatory
        DESCRIPTION
            "Total Recipients Inbound is the total number of recipients specified in all messages received from this entity since MTA initialization."
        ::= { exchmtaconnmSExchangeMTA-ConnectionsEntry 29 }

    exchmtaconnTotalRecipientsOutbound OBJECT-TYPE
        SYNTAX Counter
        ACCESS read-only
        STATUS mandatory
        DESCRIPTION
            "Total Recipients Outbound is the total number of recipients specified in all messages transmitted to this entity since MTA initialization."
        ::= { exchmtaconnmSExchangeMTA-ConnectionsEntry 30 }

    -- mSExchangeIMC MIB

    mSExchangeIMC OBJECT IDENTIFIER ::= { performance 22 }

    exchimcQueuedMTS-IN OBJECT-TYPE
        SYNTAX INTEGER
        ACCESS read-only
        STATUS mandatory
        DESCRIPTION
            "The number of messages awaiting final delivery in MS Exchange Server"
        ::= { mSExchangeIMC 1 }

    exchimcBytesQueuedMTS-IN OBJECT-TYPE
        SYNTAX INTEGER
        ACCESS read-only
        STATUS mandatory
        DESCRIPTION
            "The size, in bytes, of the messages that have been converted from Internet Mail and are awaiting final delivery within MS Exchange Server"
        ::= { mSExchangeIMC 2 }

    exchimcMessagesEnteringMTS-IN OBJECT-TYPE
        SYNTAX INTEGER
        ACCESS read-only
        STATUS mandatory
        DESCRIPTION
            "The number of messages entering the MTS-IN folder after conversion from Internet Mail format per hour"
        ::= { mSExchangeIMC 3 }

    exchimcQueuedMTS-OUT OBJECT-TYPE
        SYNTAX INTEGER
        ACCESS read-only
        STATUS mandatory
        DESCRIPTION
            "The number of messages waiting to be converted to Internet Mail format"
        ::= { mSExchangeIMC 4 }

    exchimcBytesQueuedMTS-OUT OBJECT-TYPE
        SYNTAX INTEGER
        ACCESS read-only
        STATUS mandatory
        DESCRIPTION
            "The size, in bytes, of the messages waiting to be converted to Internet Mail format"
        ::= { mSExchangeIMC 5 }

    exchimcMessagesEnteringMTS-OUT OBJECT-TYPE
        SYNTAX INTEGER
        ACCESS read-only
        STATUS mandatory
        DESCRIPTION
            "Messages that have entered the Internet Mail Service"
        ::= { mSExchangeIMC 6 }

    exchimcMessagesLeavingMTS-OUT OBJECT-TYPE
        SYNTAX INTEGER
        ACCESS read-only
        STATUS mandatory
        DESCRIPTION
            "The number of messages entering the Outbound Queue per hour"
        ::= { mSExchangeIMC 7 }

    exchimcConnectionsInbound OBJECT-TYPE
        SYNTAX INTEGER
        ACCESS read-only
        STATUS mandatory
        DESCRIPTION
            "The number of current SMTP connections to the Internet Mail Service established by other SMTP hosts"
        ::= { mSExchangeIMC 8 }

    exchimcConnectionsOutbound OBJECT-TYPE
        SYNTAX INTEGER
        ACCESS read-only
        STATUS mandatory
        DESCRIPTION
            "The number of current SMTP connections the Internet Mail Service has established to other SMTP hosts"
        ::= { mSExchangeIMC 9 }

    exchimcConnectionsTotalOutbound OBJECT-TYPE
        SYNTAX INTEGER
        ACCESS read-only
        STATUS mandatory
        DESCRIPTION
            "The total number of successful SMTP connections that the Internet Mail Service has established since it was started"
        ::= { mSExchangeIMC 10 }

    exchimcConnectionsTotalInbound OBJECT-TYPE
        SYNTAX INTEGER
        ACCESS read-only
        STATUS mandatory
        DESCRIPTION
            "The total number of SMTP connections the Internet Mail Service has accepted from other hosts since it was started"
        ::= { mSExchangeIMC 11 }

    exchimcConnectionsTotalRejected OBJECT-TYPE
        SYNTAX INTEGER
        ACCESS read-only
        STATUS mandatory
        DESCRIPTION
            "The total number of SMTP connections that the Internet Mail Service has rejected from other hosts since it was started"
        ::= { mSExchangeIMC 12 }

    exchimcConnectionsTotalFailed OBJECT-TYPE
        SYNTAX INTEGER
        ACCESS read-only
        STATUS mandatory
        DESCRIPTION
            "The total number of SMTP connections the Internet Mail Service has attempted to other hosts that failed since it was started"
        ::= { mSExchangeIMC 13 }

    exchimcQueuedOutbound OBJECT-TYPE
        SYNTAX INTEGER
        ACCESS read-only
        STATUS mandatory
        DESCRIPTION
            "The number of messages from MS Exchange Server, that are queued to be delivered to the Internet"
        ::= { mSExchangeIMC 14 }

    exchimcQueuedInbound OBJECT-TYPE
        SYNTAX INTEGER
        ACCESS read-only
        STATUS mandatory
        DESCRIPTION
            "The number of messages received from the Internet destined for MS Exchange Server"
        ::= { mSExchangeIMC 15 }

    exchimcNDRsTotalInbound OBJECT-TYPE
        SYNTAX INTEGER
        ACCESS read-only
        STATUS mandatory
        DESCRIPTION
            "The total number of Non-delivery reports generated for inbound mail"
        ::= { mSExchangeIMC 16 }

    exchimcNDRsTotalOutbound OBJECT-TYPE
        SYNTAX INTEGER
        ACCESS read-only
        STATUS mandatory
        DESCRIPTION
            "The total number of Non-delivery reports generated for outbound mail"
        ::= { mSExchangeIMC 17 }

    exchimcTotalInboundKilobytes OBJECT-TYPE
        SYNTAX INTEGER
        ACCESS read-only
        STATUS mandatory
        DESCRIPTION
            "The total kilobytes of message data transferred into the MS Exchange Server"
        ::= { mSExchangeIMC 18 }

    exchimcTotalOutboundKilobytes OBJECT-TYPE
        SYNTAX INTEGER
        ACCESS read-only
        STATUS mandatory
        DESCRIPTION
            "The total kilobytes of message data transferred out of the MS Exchange Server"
        ::= { mSExchangeIMC 19 }

    exchimcInboundMessagesTotal OBJECT-TYPE
        SYNTAX INTEGER
        ACCESS read-only
        STATUS mandatory
        DESCRIPTION
            "The total number of Internet messages delivered into MS Exchange Server"
        ::= { mSExchangeIMC 20 }

    exchimcOutboundMessagesTotal OBJECT-TYPE
        SYNTAX INTEGER
        ACCESS read-only
        STATUS mandatory
        DESCRIPTION
            "The total number of outbound messages delivered to their destinations"
        ::= { mSExchangeIMC 21 }

    exchimcInboundBytesPerHr OBJECT-TYPE
        SYNTAX INTEGER
        ACCESS read-only
        STATUS mandatory
        DESCRIPTION
            "The hourly rate of bytes transferred to the MS Exchange Server"
        ::= { mSExchangeIMC 22 }

    exchimcOutboundBytesPerHr OBJECT-TYPE
        SYNTAX INTEGER
        ACCESS read-only
        STATUS mandatory
        DESCRIPTION
            "The hourly rate of bytes transferred to the Internet"
        ::= { mSExchangeIMC 23 }

    exchimcInboundMessagesPerHr OBJECT-TYPE
        SYNTAX INTEGER
        ACCESS read-only
        STATUS mandatory
        DESCRIPTION
            "The hourly rate messages are transferred to the MS Exchange server"
        ::= { mSExchangeIMC 24 }

    exchimcOutboundMessagesPerHr OBJECT-TYPE
        SYNTAX INTEGER
        ACCESS read-only
        STATUS mandatory
        DESCRIPTION
            "The hourly rate messages are transferred to the Internet"
        ::= { mSExchangeIMC 25 }

    exchimcOutboundConnectionsPerHr OBJECT-TYPE
        SYNTAX INTEGER
        ACCESS read-only
        STATUS mandatory
        DESCRIPTION
            "The hourly rate at which outbound connections were made"
        ::= { mSExchangeIMC 26 }

    exchimcInboundConnectionsPerHr OBJECT-TYPE
        SYNTAX INTEGER
        ACCESS read-only
        STATUS mandatory
        DESCRIPTION
            "The hourly rate at which inbound connections were received"
        ::= { mSExchangeIMC 27 }

    exchimcTotalMessagesQueued OBJECT-TYPE
        SYNTAX INTEGER
        ACCESS read-only
        STATUS mandatory
        DESCRIPTION
            "Total messages waiting in the Internet Mail Service queues"
        ::= { mSExchangeIMC 28 }

    exchimcTotalKilobytesQueued OBJECT-TYPE
        SYNTAX INTEGER
        ACCESS read-only
        STATUS mandatory
        DESCRIPTION
            "Total kilobytes of message data queued in the Internet Mail Service queues"
        ::= { mSExchangeIMC 29 }

    exchimcTotalInboundRecipients OBJECT-TYPE
        SYNTAX INTEGER
        ACCESS read-only
        STATUS mandatory
        DESCRIPTION
            "Total number of recipients processed inbound since the Internet Mail Service was started"
        ::= { mSExchangeIMC 30 }

    exchimcTotalOutboundRecipients OBJECT-TYPE
        SYNTAX INTEGER
        ACCESS read-only
        STATUS mandatory
        DESCRIPTION
            "Total number of recipients processed outbound since the Internet Mail Service was started"
        ::= { mSExchangeIMC 31 }

    exchimcTotalRecipientsQueued OBJECT-TYPE
        SYNTAX INTEGER
        ACCESS read-only
        STATUS mandatory
        DESCRIPTION
            "Total number of recipients in the Internet Mail Service queues"
        ::= { mSExchangeIMC 32 }

    exchimcTotalSuccessfulConversions OBJECT-TYPE
        SYNTAX INTEGER
        ACCESS read-only
        STATUS mandatory
        DESCRIPTION
            "Total message format conversions between internet format and Exchange format that succeeded."
        ::= { mSExchangeIMC 33 }

    exchimcTotalFailedConversions OBJECT-TYPE
        SYNTAX INTEGER
        ACCESS read-only
        STATUS mandatory
        DESCRIPTION
            "Total message format conversions between internet format and Exchange format that failed."
        ::= { mSExchangeIMC 34 }

    exchimcTotalLoopsDetected OBJECT-TYPE
        SYNTAX INTEGER
        ACCESS read-only
        STATUS mandatory
        DESCRIPTION
            "Total number of messages NDRd because they appeared to be looping infinitely."
        ::= { mSExchangeIMC 35 }

    -- mSExchangeIS MIB

    mSExchangeIS OBJECT IDENTIFIER ::= { performance 23 }

    exchisRPCPacketsPerSec OBJECT-TYPE
        SYNTAX Counter
        ACCESS read-only
        STATUS mandatory
        DESCRIPTION
            "RPC Packets/sec is the rate that RPC packets are processed."
        ::= { mSExchangeIS 1 }

    exchisRPCOperationsPerSec OBJECT-TYPE
        SYNTAX Counter
        ACCESS read-only
        STATUS mandatory
        DESCRIPTION
            "RPC Operations/sec is the rate that RPC operations occur."
        ::= { mSExchangeIS 2 }

    exchisReadBytesRPCClientsPerSec OBJECT-TYPE
        SYNTAX Counter
        ACCESS read-only
        STATUS mandatory
        DESCRIPTION
            "Read Bytes RPC Clients/sec is the rate that bytes are read from RPC clients."
        ::= { mSExchangeIS 3 }

    exchisWriteBytesRPCClientsPerSec OBJECT-TYPE
        SYNTAX Counter
        ACCESS read-only
        STATUS mandatory
        DESCRIPTION
            "Write Bytes RPC Clients/sec is the rate that bytes are written to RPC clients."
        ::= { mSExchangeIS 4 }

    exchisPushNotificationsGeneratedPerSec OBJECT-TYPE
        SYNTAX Counter
        ACCESS read-only
        STATUS mandatory
        DESCRIPTION
            "Push Notifications Generated/sec is the rate at which notifications are being sent to clients that have registered for notifications of changes to tables in the information store."
        ::= { mSExchangeIS 5 }

    exchisPushNotificationsSkippedPerSec OBJECT-TYPE
        SYNTAX Counter
        ACCESS read-only
        STATUS mandatory
        DESCRIPTION
            "Push Notifications Skipped/sec is the number of push notifications that have been skipped by caching at the server."
        ::= { mSExchangeIS 6 }

    exchisRPCRequests OBJECT-TYPE
        SYNTAX INTEGER
        ACCESS read-only
        STATUS mandatory
        DESCRIPTION
            "RPC Requests is the number of client requests that are currently being processed by the information store."
        ::= { mSExchangeIS 7 }

    exchisRPCRequestsPeak OBJECT-TYPE
        SYNTAX INTEGER
        ACCESS read-only
        STATUS mandatory
        DESCRIPTION
            "RPC Requests Peak is the maximum number of client requests that were processed simultaneously by the information store since it was started."
        ::= { mSExchangeIS 8 }

    exchisUserCount OBJECT-TYPE
        SYNTAX INTEGER
        ACCESS read-only
        STATUS mandatory
        DESCRIPTION
            "User Count is the number of users connected to the information store."
        ::= { mSExchangeIS 9 }

    exchisActiveUserCount OBJECT-TYPE
        SYNTAX INTEGER
        ACCESS read-only
        STATUS mandatory
        DESCRIPTION
            "Number of user connections that have shown some activity in the last 10 minutes."
        ::= { mSExchangeIS 10 }

    exchisMaximumUsers OBJECT-TYPE
        SYNTAX INTEGER
        ACCESS read-only
        STATUS mandatory
        DESCRIPTION
            "Maximum Users is the maximum number of concurrent users since startup."
        ::= { mSExchangeIS 11 }

    exchisAnonymousUserCount OBJECT-TYPE
        SYNTAX INTEGER
        ACCESS read-only
        STATUS mandatory
        DESCRIPTION
            "Anonymous User Count is the number of anonymous users connected to the information store."
        ::= { mSExchangeIS 12 }

    exchisActiveAnonymousUserCount OBJECT-TYPE
        SYNTAX INTEGER
        ACCESS read-only
        STATUS mandatory
        DESCRIPTION
            "Number of active users."
        ::= { mSExchangeIS 13 }

    exchisMaximumAnonymousUsers OBJECT-TYPE
        SYNTAX INTEGER
        ACCESS read-only
        STATUS mandatory
        DESCRIPTION
            "The maximum number of anonymous users since startup."
        ::= { mSExchangeIS 14 }

    exchisConnectionCount OBJECT-TYPE
        SYNTAX INTEGER
        ACCESS read-only
        STATUS mandatory
        DESCRIPTION
            "Connection Count is the number of client processes connected to the information store."
        ::= { mSExchangeIS 15 }

    exchisActiveConnectionCount OBJECT-TYPE
        SYNTAX INTEGER
        ACCESS read-only
        STATUS mandatory
        DESCRIPTION
            "Number of connections that have shown some activity in the last 10 minutes."
        ::= { mSExchangeIS 16 }

    exchisMaximumConnections OBJECT-TYPE
        SYNTAX INTEGER
        ACCESS read-only
        STATUS mandatory
        DESCRIPTION
            "The maximum number of concurrent connections since startup."
        ::= { mSExchangeIS 17 }

    exchisPushNotificationsCacheSize OBJECT-TYPE
        SYNTAX INTEGER
        ACCESS read-only
        STATUS mandatory
        DESCRIPTION
            "The current size of the Push Notifications Cache."
        ::= { mSExchangeIS 18 }

    exchisPeakPushNotificationsCacheSize OBJECT-TYPE
        SYNTAX INTEGER
        ACCESS read-only
        STATUS mandatory
        DESCRIPTION
            "The maximum size of the Push Notifications Cache."
        ::= { mSExchangeIS 19 }

    exchisDatabaseSessionHitRate OBJECT-TYPE
        SYNTAX INTEGER
        ACCESS read-only
        STATUS mandatory
        DESCRIPTION
            "Database Session Hit Rate is the percent hit rate on re-using database sessions."
        ::= { mSExchangeIS 20 }

    exchisIMAPMessagesSent OBJECT-TYPE
        SYNTAX INTEGER
        ACCESS read-only
        STATUS mandatory
        DESCRIPTION
            "Messages Sent to clients connected via the IMAP external network interface."
        ::= { mSExchangeIS 22 }

    exchisIMAPCommandsIssued OBJECT-TYPE
        SYNTAX INTEGER
        ACCESS read-only
        STATUS mandatory
        DESCRIPTION
            "Total number of commands issued by clients connected via the IMAP external network interface"
        ::= { mSExchangeIS 23 }

    exchisIMAPMessageSendRate OBJECT-TYPE
        SYNTAX Counter
        ACCESS read-only
        STATUS mandatory
        DESCRIPTION
            "Rate at which messages are sent to clients connected via the IMAP external network interface."
        ::= { mSExchangeIS 24 }

    exchisIMAPCommandsIssuedRate OBJECT-TYPE
        SYNTAX Counter
        ACCESS read-only
        STATUS mandatory
        DESCRIPTION
            "Rate at which commands are issued by clients connected via the IMAP external network interface"
        ::= { mSExchangeIS 25 }

    exchisPOP3MessagesSent OBJECT-TYPE
        SYNTAX INTEGER
        ACCESS read-only
        STATUS mandatory
        DESCRIPTION
            "Messages Sent to clients connected via the POP3 external network interface."
        ::= { mSExchangeIS 26 }

    exchisPOP3CommandsIssued OBJECT-TYPE
        SYNTAX INTEGER
        ACCESS read-only
        STATUS mandatory
        DESCRIPTION
            "Total number of commands issued by clients connected via the POP3 external network interface"
        ::= { mSExchangeIS 27 }

    exchisPOP3MessagesSendRate OBJECT-TYPE
        SYNTAX Counter
        ACCESS read-only
        STATUS mandatory
        DESCRIPTION
            "Rate at which messages are sent to clients connected via the POP3 external network interface."
        ::= { mSExchangeIS 28 }

    exchisPOP3CommandsIssuedRate OBJECT-TYPE
        SYNTAX Counter
        ACCESS read-only
        STATUS mandatory
        DESCRIPTION
            "Rate at which commands are issued by clients connected via the POP3 external network interface"
        ::= { mSExchangeIS 29 }

    exchisNNTPMessagesRead OBJECT-TYPE
        SYNTAX INTEGER
        ACCESS read-only
        STATUS mandatory
        DESCRIPTION
            "NNTP Messages Read is the the total number of messages sent from the information store to NNTP clients since service startup."
        ::= { mSExchangeIS 30 }

    exchisNNTPMessagesPosted OBJECT-TYPE
        SYNTAX INTEGER
        ACCESS read-only
        STATUS mandatory
        DESCRIPTION
            "NNTP Messages Posted is the total number of messages posted by NNTP clients into the information store since service startup."
        ::= { mSExchangeIS 31 }

    exchisNNTPFailedPosts OBJECT-TYPE
        SYNTAX INTEGER
        ACCESS read-only
        STATUS mandatory
        DESCRIPTION
            "NNTP Failed Posts is the total number of messages posted by NNTP clients that were rejected due to missing required headers or other errors."
        ::= { mSExchangeIS 32 }

    exchisNewsfeedMessagesReceived OBJECT-TYPE
        SYNTAX INTEGER
        ACCESS read-only
        STATUS mandatory
        DESCRIPTION
            "Newsfeed Messages Received is the total number of messages received into the information store from NNTP newsfeeds since service startup."
        ::= { mSExchangeIS 33 }

    exchisNewsfeedInboundRejectedMessages OBJECT-TYPE
        SYNTAX INTEGER
        ACCESS read-only
        STATUS mandatory
        DESCRIPTION
            "Newsfeed Inbound Rejected Messages is the total number of messages received in newsfeeds from other NNTP servers that have been rejected as duplicates or due to errors."
        ::= { mSExchangeIS 34 }

    exchisNNTPCommandsIssued OBJECT-TYPE
        SYNTAX INTEGER
        ACCESS read-only
        STATUS mandatory
        DESCRIPTION
            "Total number of commands issued by clients connected via the NNTP external network interface"
        ::= { mSExchangeIS 35 }

    exchisNNTPMessagesReadRate OBJECT-TYPE
        SYNTAX Counter
        ACCESS read-only
        STATUS mandatory
        DESCRIPTION
            "Rate at which messages are sent to NNTP clients"
        ::= { mSExchangeIS 36 }

    exchisNNTPMessagesPostedRate OBJECT-TYPE
        SYNTAX Counter
        ACCESS read-only
        STATUS mandatory
        DESCRIPTION
            "Rate at which NNTP messages are posted by NNTP clients"
        ::= { mSExchangeIS 37 }

    exchisNNTPFailedPostsRate OBJECT-TYPE
        SYNTAX Counter
        ACCESS read-only
        STATUS mandatory
        DESCRIPTION
            "Rate at which messages posted by NNTP clients are rejected"
        ::= { mSExchangeIS 38 }

    exchisNewsfeedMessagesReceivedRate OBJECT-TYPE
        SYNTAX Counter
        ACCESS read-only
        STATUS mandatory
        DESCRIPTION
            "Rate at which messages are received into the information store from NNTP newsfeeds"
        ::= { mSExchangeIS 39 }

    exchisNewsfeedInboundRejectedMessagesRate OBJECT-TYPE
        SYNTAX Counter
        ACCESS read-only
        STATUS mandatory
        DESCRIPTION
            "Rate at which messages received in newsfeeds from other NNTP servers are rejected"
        ::= { mSExchangeIS 40 }

    exchisNNTPCommandsIssuedRate OBJECT-TYPE
        SYNTAX Counter
        ACCESS read-only
        STATUS mandatory
        DESCRIPTION
            "Rate at which commands are issued by clients connected via the NNTP external network interface"
        ::= { mSExchangeIS 41 }

    exchisNewsfeedMessagesSent OBJECT-TYPE
        SYNTAX INTEGER
        ACCESS read-only
        STATUS mandatory
        DESCRIPTION
            "Newsfeed Messages Sent is the total number of messages sent from the information store to other NNTP servers by the Internet News Service since startup."
        ::= { mSExchangeIS 42 }

    exchisNewsfeedMessagesSentPerSec OBJECT-TYPE
        SYNTAX Counter
        ACCESS read-only
        STATUS mandatory
        DESCRIPTION
            "Newsfeed Messages Sent/sec is the rate at which messages are sent from the information store to other NNTP servers by the Internet News Service."
        ::= { mSExchangeIS 43 }

    exchisNewsfeedBytesSent OBJECT-TYPE
        SYNTAX INTEGER
        ACCESS read-only
        STATUS mandatory
        DESCRIPTION
            "Newsfeed Bytes Sent is the total number of bytes sent from the information store to other NNTP servers by the Internet News Service since startup."
        ::= { mSExchangeIS 44 }

    exchisNewsfeedBytesSentPerSec OBJECT-TYPE
        SYNTAX Counter
        ACCESS read-only
        STATUS mandatory
        DESCRIPTION
            "Newsfeed Bytes Sent/sec is the rate data is sent from the information store to other NNTP servers by the Internet News Service."
        ::= { mSExchangeIS 45 }

    exchisNewsfeedOutboundRejectedMessages OBJECT-TYPE
        SYNTAX INTEGER
        ACCESS read-only
        STATUS mandatory
        DESCRIPTION
            "Newsfeed Outbound Rejected Messages is the total number of messages sent in newsfeeds to other NNTP servers that have been rejected as duplicates or due to errors since service startup."
        ::= { mSExchangeIS 46 }

    exchisNNTPOutboundConnections OBJECT-TYPE
        SYNTAX INTEGER
        ACCESS read-only
        STATUS mandatory
        DESCRIPTION
            "NNTP Outbound Connections is the total number of outbound TCP/IP connections to other NNTP servers that have been made by the Internet News Service for push or pull newsfeeds since startup."
        ::= { mSExchangeIS 47 }

    exchisNNTPCurrentOutboundConnections OBJECT-TYPE
        SYNTAX INTEGER
        ACCESS read-only
        STATUS mandatory
        DESCRIPTION
            "NNTP Current Outbound Connections is the current number of outbound TCP/IP connections from the Internet News Service to other NNTP servers for push or pull newsfeeds."
        ::= { mSExchangeIS 48 }

    exchisNumberOfArticleIndexTableRowsExpired OBJECT-TYPE
        SYNTAX INTEGER
        ACCESS read-only
        STATUS mandatory
        DESCRIPTION
            "Number of article index table rows expired"
        ::= { mSExchangeIS 49 }

    -- mSExchangeIS Public MIB

    mSExchangeIS-Public OBJECT IDENTIFIER ::= { performance 24 }

    exchispubSendQueueSize OBJECT-TYPE
        SYNTAX INTEGER
        ACCESS read-only
        STATUS mandatory
        DESCRIPTION
            "Send Queue Size is the number of messages in the public information store's send queue."
        ::= { mSExchangeIS-Public 1 }

    exchispubReceiveQueueSize OBJECT-TYPE
        SYNTAX INTEGER
        ACCESS read-only
        STATUS mandatory
        DESCRIPTION
            "Receive Queue Size is the number of messages in the public information store's receive queue."
        ::= { mSExchangeIS-Public 2 }

    exchispubCategorizationCount OBJECT-TYPE
        SYNTAX INTEGER
        ACCESS read-only
        STATUS mandatory
        DESCRIPTION
            "Categorization Count is the number of categorizations that exist in the information store. Categorizations are created when a user creates a filtered view or performs a search. When the information store must maintain an excessive number of categorizations, performance can be affected."
        ::= { mSExchangeIS-Public 3 }

    exchispubMessagesDelivered OBJECT-TYPE
        SYNTAX INTEGER
        ACCESS read-only
        STATUS mandatory
        DESCRIPTION
            "Messages Delivered is the total number of messages delivered to all recipients since startup."
        ::= { mSExchangeIS-Public 4 }

    exchispubMessageRecipientsDelivered OBJECT-TYPE
        SYNTAX INTEGER
        ACCESS read-only
        STATUS mandatory
        DESCRIPTION
            "Message Recipients Delivered is the total number of recipients that have received a message since startup."
        ::= { mSExchangeIS-Public 5 }

    exchispubMessagesSent OBJECT-TYPE
        SYNTAX INTEGER
        ACCESS read-only
        STATUS mandatory
        DESCRIPTION
            "Messages Sent is the total number of messages sent to other storage providers via the message transfer agent (MTA) since startup."
        ::= { mSExchangeIS-Public 6 }

    exchispubMessagesSubmitted OBJECT-TYPE
        SYNTAX INTEGER
        ACCESS read-only
        STATUS mandatory
        DESCRIPTION
            "Messages Submitted is the total number of messages submitted by clients since startup."
        ::= { mSExchangeIS-Public 7 }

    exchispubSingleInstanceRatio OBJECT-TYPE
        SYNTAX INTEGER
        ACCESS read-only
        STATUS mandatory
        DESCRIPTION
            "Single Instance Ratio is the average number of references to each message in the public information store."
        ::= { mSExchangeIS-Public 8 }

    exchispubMessagesDeliveredPerMin OBJECT-TYPE
        SYNTAX INTEGER
        ACCESS read-only
        STATUS mandatory
        DESCRIPTION
            "Messages Delivered/min is the rate that messages are delivered to all recipients."
        ::= { mSExchangeIS-Public 10 }

    exchispubMessageRecipientsDeliveredPerMin OBJECT-TYPE
        SYNTAX INTEGER
        ACCESS read-only
        STATUS mandatory
        DESCRIPTION
            "Message Recipients Delivered/min is the rate that recipients receive messages."
        ::= { mSExchangeIS-Public 11 }

    exchispubMessagesSentPerMin OBJECT-TYPE
        SYNTAX INTEGER
        ACCESS read-only
        STATUS mandatory
        DESCRIPTION
            "Messages Sent/min is the rate that messages are sent to other storage providers via the message transfter agent (MTA)."
        ::= { mSExchangeIS-Public 12 }

    exchispubMessageSubmittedPerMin OBJECT-TYPE
        SYNTAX INTEGER
        ACCESS read-only
        STATUS mandatory
        DESCRIPTION
            "Messages Submitted/min is the rate that messages are submitted by clients."
        ::= { mSExchangeIS-Public 13 }

    exchispubAverageTimeForDelivery OBJECT-TYPE
        SYNTAX INTEGER
        ACCESS read-only
        STATUS mandatory
        DESCRIPTION
            "Average Time for Delivery is the average time between the submission of a message to the information store and submission to the messages transfer agent (MTA) for the last 10 messages."
        ::= { mSExchangeIS-Public 14 }

    exchispubAverageTimeForLocalDelivery OBJECT-TYPE
        SYNTAX INTEGER
        ACCESS read-only
        STATUS mandatory
        DESCRIPTION
            "Average Time for Local Delivery is the average time between the submission of a message to the information store and the delivery to all local recipients (recipients on the same server) for the last 10 messages."
        ::= { mSExchangeIS-Public 15 }

    exchispubTotalSizeOfRecoverableItems OBJECT-TYPE
        SYNTAX INTEGER
        ACCESS read-only
        STATUS mandatory
        DESCRIPTION
            "Total Size of Recoverable Items is the total size in kilobytes of items retained for Item Recovery"
        ::= { mSExchangeIS-Public 16 }

    exchispubTotalCountOfRecoverableItems OBJECT-TYPE
        SYNTAX INTEGER
        ACCESS read-only
        STATUS mandatory
        DESCRIPTION
            "Total Count of Recoverable Items is the total number of items retained for Item Recovery"
        ::= { mSExchangeIS-Public 17 }

    exchispubReplicationMessagesSent OBJECT-TYPE
        SYNTAX INTEGER
        ACCESS read-only
        STATUS mandatory
        DESCRIPTION
            "Replication Messages Sent is the total number of replication messages that have been sent to other servers since service startup."
        ::= { mSExchangeIS-Public 18 }

    exchispubReplicationFolderTreeMessagesSent OBJECT-TYPE
        SYNTAX INTEGER
        ACCESS read-only
        STATUS mandatory
        DESCRIPTION
            "Replication Folder Tree Messages Sent is the number of replication messages due to public folder hierarchy changes that have been sent to other servers since service startup."
        ::= { mSExchangeIS-Public 19 }

    exchispubReplicationFolderChangesSent OBJECT-TYPE
        SYNTAX INTEGER
        ACCESS read-only
        STATUS mandatory
        DESCRIPTION
            "Replication Folder Tree Messages Sent is the number of replication messages due to public folder hierarchy changes that have been sent to other servers since service startup."
        ::= { mSExchangeIS-Public 20 }

    exchispubReplicationFolderDataMessagesSent OBJECT-TYPE
        SYNTAX INTEGER
        ACCESS read-only
        STATUS mandatory
        DESCRIPTION
            "Replication Folder Data Message Messages sent is the number of replication messages due to changes to items in public folders that have been sent to other servers since service startup."
        ::= { mSExchangeIS-Public 21 }

    exchispubReplicationMessageChangesSent OBJECT-TYPE
        SYNTAX INTEGER
        ACCESS read-only
        STATUS mandatory
        DESCRIPTION
            "Replication Message Changes Sent is the number of changes to items in public folders that have been replicated to other servers since service startup."
        ::= { mSExchangeIS-Public 22 }

    exchispubReplicationStatusMessagesSent OBJECT-TYPE
        SYNTAX INTEGER
        ACCESS read-only
        STATUS mandatory
        DESCRIPTION
            "Replication Status Messages Sent is the number of replication status request or response messages that have been sent to other servers since service startup."
        ::= { mSExchangeIS-Public 23 }

    exchispubReplicationBackfillRequestsSent OBJECT-TYPE
        SYNTAX INTEGER
        ACCESS read-only
        STATUS mandatory
        DESCRIPTION
            "Replication Backfill Requests Sent is the number of backfill request replication messages that have been sent to other servers since service startup."
        ::= { mSExchangeIS-Public 24 }

    exchispubReplicationBackfillDataMessagesSent OBJECT-TYPE
        SYNTAX INTEGER
        ACCESS read-only
        STATUS mandatory
        DESCRIPTION
            "Replication Backfill Data Messages Sent is the number of replication messages sent in response to backfill requests from other servers since service startup."
        ::= { mSExchangeIS-Public 25 }

    exchispubReplicationMessagesReceived OBJECT-TYPE
        SYNTAX INTEGER
        ACCESS read-only
        STATUS mandatory
        DESCRIPTION
            "Replication Messages Received is the total number of replication messages received from other servers since service startup."
        ::= { mSExchangeIS-Public 26 }

    exchispubReplicationFolderTreeMessagesReceived OBJECT-TYPE
        SYNTAX INTEGER
        ACCESS read-only
        STATUS mandatory
        DESCRIPTION
            "Replication Folder Tree Messages Received is the number of replication messages due to public folder hierarchy changes that have been received from other servers since service startup."
        ::= { mSExchangeIS-Public 27 }

    exchispubReplicationFolderChangesReceived OBJECT-TYPE
        SYNTAX INTEGER
        ACCESS read-only
        STATUS mandatory
        DESCRIPTION
            "Replication Folder Changes Received is the number of folder changes that have been replicated from other servers since service startup."
        ::= { mSExchangeIS-Public 28 }

    exchispubReplicationFolderDataMessagesReceived OBJECT-TYPE
        SYNTAX INTEGER
        ACCESS read-only
        STATUS mandatory
        DESCRIPTION
            "Replication Folder Data Messages Received is the number of replication messages due to changes to items in public folders that have been received from other service since service startup."
        ::= { mSExchangeIS-Public 29 }

    exchispubReplicationMessageChangesReceived OBJECT-TYPE
        SYNTAX INTEGER
        ACCESS read-only
        STATUS mandatory
        DESCRIPTION
            "Replication Message Changes Received is the number of changes to items in public folders that have been received from other servers since service startup."
        ::= { mSExchangeIS-Public 30 }

    exchispubReplicationStatusMessagesReceived OBJECT-TYPE
        SYNTAX INTEGER
        ACCESS read-only
        STATUS mandatory
        DESCRIPTION
            "Status Messages Received is the number of replication status request or response messages that have been received from other servers since service startup."
        ::= { mSExchangeIS-Public 31 }

    exchispubReplicationBackfillRequestsReceived OBJECT-TYPE
        SYNTAX INTEGER
        ACCESS read-only
        STATUS mandatory
        DESCRIPTION
            "Replication Backfill Requests Received is the number of backfill request replication messages that have been received from other servers since service startup."
        ::= { mSExchangeIS-Public 32 }

    exchispubReplicationBackfillDataMessagesReceived OBJECT-TYPE
        SYNTAX INTEGER
        ACCESS read-only
        STATUS mandatory
        DESCRIPTION
            "Replication Backfill Data Messages Received is the number of replication messages received from other servers in response to backfill requests since service startup."
        ::= { mSExchangeIS-Public 33 }

    exchispubReplicationReceiveQueueSize OBJECT-TYPE
        SYNTAX INTEGER
        ACCESS read-only
        STATUS mandatory
        DESCRIPTION
            "Replication Receive Queue Size is the number of replication messages waiting to be processed."
        ::= { mSExchangeIS-Public 34 }

    exchispubNumberOfMessagesExpiredFromPublicFolders OBJECT-TYPE
        SYNTAX INTEGER
        ACCESS read-only
        STATUS mandatory
        DESCRIPTION
            "Number of messages expired from public folders"
        ::= { mSExchangeIS-Public 35 }

    exchispubClientLogons OBJECT-TYPE
        SYNTAX INTEGER
        ACCESS read-only
        STATUS mandatory
        DESCRIPTION
            "Client Logons is the number of clients (including system processes) currently logged on."
        ::= { mSExchangeIS-Public 36 }

    exchispubActiveClientLogons OBJECT-TYPE
        SYNTAX INTEGER
        ACCESS read-only
        STATUS mandatory
        DESCRIPTION
            "Active Client Logons is the number of clients that performed any action within the last ten minute time interval."
        ::= { mSExchangeIS-Public 37 }

    exchispubPeakClientLogons OBJECT-TYPE
        SYNTAX INTEGER
        ACCESS read-only
        STATUS mandatory
        DESCRIPTION
            "Peak Client Logons is the maximum number of concurrent client logons since service startup."
        ::= { mSExchangeIS-Public 38 }

    exchispubFolderOpensPerSec OBJECT-TYPE
        SYNTAX Counter
        ACCESS read-only
        STATUS mandatory
        DESCRIPTION
            "Folder opens/sec is the rate that requests to open folders are submitted to the information store."
        ::= { mSExchangeIS-Public 41 }

    exchispubMessageOpensPerSec OBJECT-TYPE
        SYNTAX Counter
        ACCESS read-only
        STATUS mandatory
        DESCRIPTION
            "Message Opens/sec is the rate that requests to open messages are submitted to the information store."
        ::= { mSExchangeIS-Public 42 }

    -- mSExchangeIS Private MIB

    mSExchangeIS-Private OBJECT IDENTIFIER ::= { performance 25 }

    exchisprivSendQueueSize OBJECT-TYPE
        SYNTAX INTEGER
        ACCESS read-only
        STATUS mandatory
        DESCRIPTION
            "Send Queue Size is the number of messages in the private information store's send queue."
        ::= { mSExchangeIS-Private 1 }

    exchisprivReceiveQueueSize OBJECT-TYPE
        SYNTAX INTEGER
        ACCESS read-only
        STATUS mandatory
        DESCRIPTION
            "Receive Queue Size is the number of messages in the private information store's receive queue."
        ::= { mSExchangeIS-Private 2 }

    exchisprivCategorizationCount OBJECT-TYPE
        SYNTAX INTEGER
        ACCESS read-only
        STATUS mandatory
        DESCRIPTION
            "Categorization Count is the number of categorizations that exist in the private information store. Categorizations are created when a user creates a filtered view or performs a search. When the information store must maintain an excessive number of categorizations, performance can be affected."
        ::= { mSExchangeIS-Private 3 }

    exchisprivMessagesDelivered OBJECT-TYPE
        SYNTAX INTEGER
        ACCESS read-only
        STATUS mandatory
        DESCRIPTION
            "Messages Delivered is the total number of messages delivered to all recipients since startup."
        ::= { mSExchangeIS-Private 4 }

    exchisprivMessageRecipientsDelivered OBJECT-TYPE
        SYNTAX INTEGER
        ACCESS read-only
        STATUS mandatory
        DESCRIPTION
            "Message Recipients Delivered is the total number of recipients that have received a message since startup."
        ::= { mSExchangeIS-Private 5 }

    exchisprivMessagesSent OBJECT-TYPE
        SYNTAX INTEGER
        ACCESS read-only
        STATUS mandatory
        DESCRIPTION
            "Messages Sent is the total number of messages sent to other storage providers via the message transfter agent (MTA) since startup."
        ::= { mSExchangeIS-Private 6 }

    exchisprivMessagesSubmitted OBJECT-TYPE
        SYNTAX INTEGER
        ACCESS read-only
        STATUS mandatory
        DESCRIPTION
            "Messages Submitted is the total number of messages submitted by clients since service startup."
        ::= { mSExchangeIS-Private 7 }

    exchisprivSingleInstanceRatio OBJECT-TYPE
        SYNTAX INTEGER
        ACCESS read-only
        STATUS mandatory
        DESCRIPTION
            "Single Instance Ratio is the average number of references to each message in the private information store."
        ::= { mSExchangeIS-Private 8 }

    exchisprivMessagesDeliveredPerMin OBJECT-TYPE
        SYNTAX INTEGER
        ACCESS read-only
        STATUS mandatory
        DESCRIPTION
            "Messages Delivered/min is the rate that messages are delivered to all recipients."
        ::= { mSExchangeIS-Private 10 }

    exchisprivMessageRecipientsDeliveredPerMin OBJECT-TYPE
        SYNTAX INTEGER
        ACCESS read-only
        STATUS mandatory
        DESCRIPTION
            "Message Recipients Delivered/min is the rate that recipients receive messages."
        ::= { mSExchangeIS-Private 11 }

    exchisprivMessagesSentPerMin OBJECT-TYPE
        SYNTAX INTEGER
        ACCESS read-only
        STATUS mandatory
        DESCRIPTION
            "Messages Sent/min is the rate that messages are sent to other storage providers via the message transfter agent (MTA)."
        ::= { mSExchangeIS-Private 12 }

    exchisprivMessagesSubmittedPerMin OBJECT-TYPE
        SYNTAX INTEGER
        ACCESS read-only
        STATUS mandatory
        DESCRIPTION
            "Messages Submitted/min is the rate that messages are submitted by clients."
        ::= { mSExchangeIS-Private 13 }

    exchisprivAverageDeliveryTime OBJECT-TYPE
        SYNTAX INTEGER
        ACCESS read-only
        STATUS mandatory
        DESCRIPTION
            "Average Delivery Time is the average time between the submission of a message to the information store and submission to the message transfer agent (MTA) for the last 10 messages."
        ::= { mSExchangeIS-Private 14 }

    exchisprivAverageLocalDeliveryTime OBJECT-TYPE
        SYNTAX INTEGER
        ACCESS read-only
        STATUS mandatory
        DESCRIPTION
            "Average Local Delivery Time is the average time between the submission of a message to the information store and the delivery to all local recipients (recipients on the same server) for the last 10 messages."
        ::= { mSExchangeIS-Private 15 }

    exchisprivTotalSizeOfRecoverableItems OBJECT-TYPE
        SYNTAX INTEGER
        ACCESS read-only
        STATUS mandatory
        DESCRIPTION
            "Total Size of Recoverable Items is the total size in kilobytes of items retained for Item Recovery"
        ::= { mSExchangeIS-Private 16 }

    exchisprivTotalCountOfRecoverableItems OBJECT-TYPE
        SYNTAX INTEGER
        ACCESS read-only
        STATUS mandatory
        DESCRIPTION
            "Total Count of Recoverable Items is the total number of items retained for Item Recovery"
        ::= { mSExchangeIS-Private 17 }

    exchisprivClientLogons OBJECT-TYPE
        SYNTAX INTEGER
        ACCESS read-only
        STATUS mandatory
        DESCRIPTION
            "Client Logons is the number of clients (including system processes) currently logged on."
        ::= { mSExchangeIS-Private 36 }

    exchisprivActiveClientLogons OBJECT-TYPE
        SYNTAX INTEGER
        ACCESS read-only
        STATUS mandatory
        DESCRIPTION
            "Active Client Logons is the number of clients that performed any action within the last ten minute time interval."
        ::= { mSExchangeIS-Private 37 }

    exchisprivPeakClientLogons OBJECT-TYPE
        SYNTAX INTEGER
        ACCESS read-only
        STATUS mandatory
        DESCRIPTION
            "Peak Client Logons is the maximum number of concurrent client logons since the service started."
        ::= { mSExchangeIS-Private 38 }

    exchisprivLocalDeliveries OBJECT-TYPE
        SYNTAX INTEGER
        ACCESS read-only
        STATUS mandatory
        DESCRIPTION
            "Total number of messages delivered locally"
        ::= { mSExchangeIS-Private 39 }

    exchisprivLocalDeliveryRate OBJECT-TYPE
        SYNTAX Counter
        ACCESS read-only
        STATUS mandatory
        DESCRIPTION
            "Rate at which messages are delivered locally"
        ::= { mSExchangeIS-Private 40 }

    exchisprivFolderOpensPerSec OBJECT-TYPE
        SYNTAX Counter
        ACCESS read-only
        STATUS mandatory
        DESCRIPTION
            "Folder Opens/sec is the rate that requests to open folders are submitted to the information store."
        ::= { mSExchangeIS-Private 41 }

    exchisprivMessageOpensPerSec OBJECT-TYPE
        SYNTAX Counter
        ACCESS read-only
        STATUS mandatory
        DESCRIPTION
            "Message Opens/sec is the rate that requests to open messages are submitted to the information store."
        ::= { mSExchangeIS-Private 42 }

    -- mSExchangeDS MIB

    mSExchangeDS OBJECT IDENTIFIER ::= { performance 26 }

    exchdsAccessViolations OBJECT-TYPE
        SYNTAX INTEGER
        ACCESS read-only
        STATUS mandatory
        DESCRIPTION
            "Access Violations is the number of times that directory service write operations were refused for security reasons."
        ::= { mSExchangeDS 1 }

    exchdsABBrowsesPerSec OBJECT-TYPE
        SYNTAX Counter
        ACCESS read-only
        STATUS mandatory
        DESCRIPTION
            "AB Browses/sec is the rate at which Address Book clients perform browse operations."
        ::= { mSExchangeDS 2 }

    exchdsABReadsPerSec OBJECT-TYPE
        SYNTAX Counter
        ACCESS read-only
        STATUS mandatory
        DESCRIPTION
            "AB Reads/sec is the rate at which Address Book clients perform read operations."
        ::= { mSExchangeDS 3 }

    exchdsExDSReadsPerSec OBJECT-TYPE
        SYNTAX Counter
        ACCESS read-only
        STATUS mandatory
        DESCRIPTION
            "ExDS Reads/sec is the rate at which Extended Directory Service clients perform read operations."
        ::= { mSExchangeDS 4 }

    exchdsReplicationUpdatesPerSec OBJECT-TYPE
        SYNTAX Counter
        ACCESS read-only
        STATUS mandatory
        DESCRIPTION
            "Replication Updates/sec is the rate at which replication updates are applied by the local directory service.  This indicates how much replication activity is occuring on the server."
        ::= { mSExchangeDS 5 }

    exchdsThreadsInUse OBJECT-TYPE
        SYNTAX INTEGER
        ACCESS read-only
        STATUS mandatory
        DESCRIPTION
            "Threads in Use is the current number of threads in use by the directory service (different than the number of threads in the directory service process).  Threads in Use is the number of RPC-generated threads currently in API calls and can be used to indicate whether additional processors could be of benefit."
        ::= { mSExchangeDS 6 }

    exchdsABWritesPerSec OBJECT-TYPE
        SYNTAX Counter
        ACCESS read-only
        STATUS mandatory
        DESCRIPTION
            "AB Writes/sec is the rate at which Address Book clients perform write operations."
        ::= { mSExchangeDS 7 }

    exchdsExDSWritesPerSec OBJECT-TYPE
        SYNTAX Counter
        ACCESS read-only
        STATUS mandatory
        DESCRIPTION
            "ExDS Writes/sec is the rate at which Extended Directory Service clients perform write operations."
        ::= { mSExchangeDS 8 }

    exchdsExDSClientSessions OBJECT-TYPE
        SYNTAX INTEGER
        ACCESS read-only
        STATUS mandatory
        DESCRIPTION
            "ExDS Client Sessions is the number of connected Extended Directory Service client sessions.  This indicates the number of connections from other Microsoft Exchange services and the Microsoft Exchange Administrator program."
        ::= { mSExchangeDS 9 }

    exchdsABClientSessions OBJECT-TYPE
        SYNTAX INTEGER
        ACCESS read-only
        STATUS mandatory
        DESCRIPTION
            "AB Client Sessions is the number of connected Address Book client sessions."
        ::= { mSExchangeDS 10 }

    exchdsPendingReplicationSynchronizations OBJECT-TYPE
        SYNTAX INTEGER
        ACCESS read-only
        STATUS mandatory
        DESCRIPTION
            "Pending Replication Synchronizations is the number of directory synchronizations that are queued for this server but not yet processed."
        ::= { mSExchangeDS 11 }

    exchdsRemainingReplicationUpdates OBJECT-TYPE
        SYNTAX INTEGER
        ACCESS read-only
        STATUS mandatory
        DESCRIPTION
            "Remaining Replication Updates is the number of object modifications received in the current directory replication update packet that have not yet been applied to the local server."
        ::= { mSExchangeDS 12 }

    exchdsObjectsReplicatedOutPerSec OBJECT-TYPE
        SYNTAX Counter
        ACCESS read-only
        STATUS mandatory
        DESCRIPTION
            "This is the number of objects replicated out per second from this machine to other Directory Servers."
        ::= { mSExchangeDS 13 }

    exchdsAddressBookViewReadsPerSec OBJECT-TYPE
        SYNTAX Counter
        ACCESS read-only
        STATUS mandatory
        DESCRIPTION
            "Number of directory objects read per second by the View Consistency Checker."
        ::= { mSExchangeDS 14 }

    exchdsAddressBookViewWritesPerSec OBJECT-TYPE
        SYNTAX Counter
        ACCESS read-only
        STATUS mandatory
        DESCRIPTION
            "Number of Address Book View containers created per second by the View Consistency Checker."
        ::= { mSExchangeDS 15 }

    exchdsAddressBookViewModifiesPerSec OBJECT-TYPE
        SYNTAX Counter
        ACCESS read-only
        STATUS mandatory
        DESCRIPTION
            "Number of directory objects modified per second by the View Consistency Checker."
        ::= { mSExchangeDS 16 }

    exchdsLDAPSearches OBJECT-TYPE
        SYNTAX INTEGER
        ACCESS read-only
        STATUS mandatory
        DESCRIPTION
            "Total number of LDAP searches performed since the DSA started."
        ::= { mSExchangeDS 17 }

    exchdsLDAPSearchesPerSec OBJECT-TYPE
        SYNTAX Counter
        ACCESS read-only
        STATUS mandatory
        DESCRIPTION
            "LDAP Searches/sec is the rate at which LDAP clients perform search operations."
        ::= { mSExchangeDS 18 }

    -- web Proxy Server Service MIB

    web-Proxy-Server-Service OBJECT IDENTIFIER ::= { performance 27 }

    webproxysrvrUpstreamBytesSentPerSec OBJECT-TYPE
        SYNTAX INTEGER
        ACCESS read-only
        STATUS mandatory
        DESCRIPTION
            "Upstream Bytes Sent/sec is the rate at which data bytes are sent by the Web Proxy Server to remote servers on the Internet or to a chained Web Proxy Server."
        ::= { web-Proxy-Server-Service 1 }

    webproxysrvrUpstreamBytesReceivedPerSec OBJECT-TYPE
        SYNTAX INTEGER
        ACCESS read-only
        STATUS mandatory
        DESCRIPTION
            "Upstream Bytes Received/sec is the rate at which data bytes are received by the Web Proxy Server from remote servers on the Internet or from a chained Web Proxy Server in response to requests from this Proxy."
        ::= { web-Proxy-Server-Service 2 }

    webproxysrvrUpstreamBytesTotalPerSec OBJECT-TYPE
        SYNTAX INTEGER
        ACCESS read-only
        STATUS mandatory
        DESCRIPTION
            "Upstream Bytes Total/sec is the sum of Inet Bytes Sent/sec and Bytes Received/sec. This is the total rate for all bytes transferred between the Proxy Server and remote servers on the Internet or a chained Web Proxy Server."
        ::= { web-Proxy-Server-Service 3 }

    webproxysrvrClientBytesSentPerSec OBJECT-TYPE
        SYNTAX INTEGER
        ACCESS read-only
        STATUS mandatory
        DESCRIPTION
            "Client Bytes Sent/sec is the rate at which data bytes are sent by the Web Proxy Server to Web Proxy clients."
        ::= { web-Proxy-Server-Service 4 }

    webproxysrvrClientBytesReceivedPerSec OBJECT-TYPE
        SYNTAX INTEGER
        ACCESS read-only
        STATUS mandatory
        DESCRIPTION
            "Client Bytes Received/sec is the rate at which data bytes are received by the Web Proxy Server from Web Proxy clients."
        ::= { web-Proxy-Server-Service 5 }

    webproxysrvrClientBytesTotalPerSec OBJECT-TYPE
        SYNTAX INTEGER
        ACCESS read-only
        STATUS mandatory
        DESCRIPTION
            "Client Bytes Total/sec is the sum of Client Bytes Sent/sec and Bytes Received/sec. This is the total rate for all bytes transferred between the Web Proxy Server and Web Proxy clients."
        ::= { web-Proxy-Server-Service 6 }

    webproxysrvrSSLClientBytesSentPerSec OBJECT-TYPE
        SYNTAX INTEGER
        ACCESS read-only
        STATUS mandatory
        DESCRIPTION
            "SSL Client Bytes Sent/sec is the rate at which Secure Sockets Layer (SSL) data bytes are sent by the Web Proxy Server to secured Web Proxy clients."
        ::= { web-Proxy-Server-Service 7 }

    webproxysrvrSSLClientBytesReceivedPerSec OBJECT-TYPE
        SYNTAX INTEGER
        ACCESS read-only
        STATUS mandatory
        DESCRIPTION
            "SSL Client Bytes Received/sec is the rate at which Secure Sockets Layer (SSL) data bytes are received by the Web Proxy Server from secured Web Proxy clients."
        ::= { web-Proxy-Server-Service 8 }

    webproxysrvrSSLClientBytesTotalPerSec OBJECT-TYPE
        SYNTAX INTEGER
        ACCESS read-only
        STATUS mandatory
        DESCRIPTION
            "SSL Client Bytes Total/sec is the sum of SSL Client Bytes Sent/sec and Bytes Received/sec. This is the total rate for all bytes transferred between the Web Proxy Server and secured Web Proxy clients."
        ::= { web-Proxy-Server-Service 9 }

    webproxysrvrSocksClientBytesSentPerSec OBJECT-TYPE
        SYNTAX INTEGER
        ACCESS read-only
        STATUS mandatory
        DESCRIPTION
            "Socks Client Bytes Sent/sec is the rate at which data is transferred by the Web Proxy Server from Socks clients to connected servers."
        ::= { web-Proxy-Server-Service 10 }

    webproxysrvrSocksClientBytesReceivedPerSec OBJECT-TYPE
        SYNTAX INTEGER
        ACCESS read-only
        STATUS mandatory
        DESCRIPTION
            "Socks Client Bytes Received/sec is the rate at which data is transferred by the Web Proxy Server from connected servers to Socks clients."
        ::= { web-Proxy-Server-Service 11 }

    webproxysrvrSocksClientBytesTotalPerSec OBJECT-TYPE
        SYNTAX INTEGER
        ACCESS read-only
        STATUS mandatory
        DESCRIPTION
            "Socks Client Bytes Total/sec is the sum of Socks Client Bytes Sent/sec and Bytes Received/sec. This is the total rate for all bytes transferred between the Web Proxy Server and Socks clients."
        ::= { web-Proxy-Server-Service 12 }

    webproxysrvrCurrentUsers OBJECT-TYPE
        SYNTAX INTEGER
        ACCESS read-only
        STATUS mandatory
        DESCRIPTION
            "Current Users is the number of users currently connected to the Web Proxy Server."
        ::= { web-Proxy-Server-Service 13 }

    webproxysrvrTotalUsers OBJECT-TYPE
        SYNTAX INTEGER
        ACCESS read-only
        STATUS mandatory
        DESCRIPTION
            "Total Users is the total number of users that have ever connected to the Web Proxy Server."
        ::= { web-Proxy-Server-Service 14 }

    webproxysrvrMaximumUsers OBJECT-TYPE
        SYNTAX INTEGER
        ACCESS read-only
        STATUS mandatory
        DESCRIPTION
            "Maximum Users is the maximum number of users that have connected to the Web Proxy Server simultaneously."
        ::= { web-Proxy-Server-Service 15 }

    webproxysrvrFtpRequests OBJECT-TYPE
        SYNTAX INTEGER
        ACCESS read-only
        STATUS mandatory
        DESCRIPTION
            "Ftp Requests is the number of Ftp requests that have been made to the Web Proxy Server."
        ::= { web-Proxy-Server-Service 16 }

    webproxysrvrGopherRequests OBJECT-TYPE
        SYNTAX INTEGER
        ACCESS read-only
        STATUS mandatory
        DESCRIPTION
            "Gopher Requests is the number of Gopher requests that have been made to the Web Proxy Server."
        ::= { web-Proxy-Server-Service 17 }

    webproxysrvrHttpRequests OBJECT-TYPE
        SYNTAX INTEGER
        ACCESS read-only
        STATUS mandatory
        DESCRIPTION
            "Http Requests is the number of Http requests that have been made to the Web Proxy Server."
        ::= { web-Proxy-Server-Service 18 }

    webproxysrvrTotalRequests OBJECT-TYPE
        SYNTAX INTEGER
        ACCESS read-only
        STATUS mandatory
        DESCRIPTION
            "Total Requests is the total number of requests that have ever been made to the Web Proxy Server."
        ::= { web-Proxy-Server-Service 19 }

    webproxysrvrTotalSuccessfulRequests OBJECT-TYPE
        SYNTAX INTEGER
        ACCESS read-only
        STATUS mandatory
        DESCRIPTION
            "Total Successful Requests is the total number of requests that have been successfully processed by the Web Proxy Server."
        ::= { web-Proxy-Server-Service 20 }

    webproxysrvrTotalFailingRequests OBJECT-TYPE
        SYNTAX INTEGER
        ACCESS read-only
        STATUS mandatory
        DESCRIPTION
            "Total Failing Requests is the total number of requests that have failed to be processed by the Web Proxy Server due to errors.  Errors can be the result of the Web Proxy Server failing to locate a requested server URL on the Internet or because the client failed to be authorized access to the requested URL."
        ::= { web-Proxy-Server-Service 21 }

    webproxysrvrTotalCacheFetches OBJECT-TYPE
        SYNTAX INTEGER
        ACCESS read-only
        STATUS mandatory
        DESCRIPTION
            "Total Cache Fetches is the total number of requests that have been served by using cached data from the Web Proxy Server cache."
        ::= { web-Proxy-Server-Service 22 }

    webproxysrvrTotalUpstreamFetches OBJECT-TYPE
        SYNTAX INTEGER
        ACCESS read-only
        STATUS mandatory
        DESCRIPTION
            "Total Upstream Fetches is the total number of requests that have been served by using data retrieved from servers on the Internet or from a chained Web Proxy Server."
        ::= { web-Proxy-Server-Service 23 }

    webproxysrvrCacheHitRatioPercent OBJECT-TYPE
        SYNTAX INTEGER
        ACCESS read-only
        STATUS mandatory
        DESCRIPTION
            "Cache Hit Ratio is the percentage of requests that have been served using cached data out of the total number of requests to the Web Proxy Server."
        ::= { web-Proxy-Server-Service 24 }

    webproxysrvrSitesDenied OBJECT-TYPE
        SYNTAX INTEGER
        ACCESS read-only
        STATUS mandatory
        DESCRIPTION
            "Sites Denied is the total number of Internet sites to which the Web Proxy Server has denied access."
        ::= { web-Proxy-Server-Service 25 }

    webproxysrvrSitesGranted OBJECT-TYPE
        SYNTAX INTEGER
        ACCESS read-only
        STATUS mandatory
        DESCRIPTION
            "Sites Granted is the total number of Internet sites to which the Web Proxy Server has granted access."
        ::= { web-Proxy-Server-Service 26 }

    webproxysrvrDNSCacheEntries OBJECT-TYPE
        SYNTAX INTEGER
        ACCESS read-only
        STATUS mandatory
        DESCRIPTION
            "DNS Cache Entries is the current number of DNS domain name entries cached by the Web Proxy Server."
        ::= { web-Proxy-Server-Service 27 }

    webproxysrvrDNSRetrievals OBJECT-TYPE
        SYNTAX INTEGER
        ACCESS read-only
        STATUS mandatory
        DESCRIPTION
            "DNS Retrievals is the total number of DNS domain names that have been retrieved by the Web Proxy Server."
        ::= { web-Proxy-Server-Service 28 }

    webproxysrvrDNSCacheFlushes OBJECT-TYPE
        SYNTAX INTEGER
        ACCESS read-only
        STATUS mandatory
        DESCRIPTION
            "DNS Cache Flushes is the total number of times that the DNS domain name cache has been flushed or cleared by the Web Proxy Server."
        ::= { web-Proxy-Server-Service 29 }

    webproxysrvrDNSCacheHits OBJECT-TYPE
        SYNTAX INTEGER
        ACCESS read-only
        STATUS mandatory
        DESCRIPTION
            "DNS Cache Hits is the total number of times a DNS domain name was found within the DNS Cache."
        ::= { web-Proxy-Server-Service 30 }

    webproxysrvrDNSCacheHitsPercent OBJECT-TYPE
        SYNTAX INTEGER
        ACCESS read-only
        STATUS mandatory
        DESCRIPTION
            "DNS Cache Hits % is the percentage of DNS domain names served from the Web Proxy Server cache, from the total of all DNS entries that have been retrieved by the Web Proxy Server."
        ::= { web-Proxy-Server-Service 31 }

    webproxysrvrHTTPSSessions OBJECT-TYPE
        SYNTAX INTEGER
        ACCESS read-only
        STATUS mandatory
        DESCRIPTION
            "HTTPS sessions is the total number of HTTP-secured sessions serviced by the Secure Sockets Layer (SSL) tunnel."
        ::= { web-Proxy-Server-Service 33 }

    webproxysrvrSNEWSSessions OBJECT-TYPE
        SYNTAX INTEGER
        ACCESS read-only
        STATUS mandatory
        DESCRIPTION
            "SNEWS sessions is the total number of SNEWS sessions serviced by the Secure Sockets Layer (SSL) tunnel."
        ::= { web-Proxy-Server-Service 34 }

    webproxysrvrUnknownSSLSessions OBJECT-TYPE
        SYNTAX INTEGER
        ACCESS read-only
        STATUS mandatory
        DESCRIPTION
            "Unknown SSL sessions is the total number of unknown Secure Sockets Layer (SSL) sessions serviced by the SSL tunnel."
        ::= { web-Proxy-Server-Service 35 }

    webproxysrvrTotalSSLSessions OBJECT-TYPE
        SYNTAX INTEGER
        ACCESS read-only
        STATUS mandatory
        DESCRIPTION
            "Total SSL sessions is the total number of Secure Sockets Layer (SSL) sessions serviced by the SSL tunnel."
        ::= { web-Proxy-Server-Service 36 }

    webproxysrvrSocksSessions OBJECT-TYPE
        SYNTAX INTEGER
        ACCESS read-only
        STATUS mandatory
        DESCRIPTION
            "Socks sessions is the current number of active sessions between Socks clients and connected servers serviced by the Web Proxy Server."
        ::= { web-Proxy-Server-Service 37 }

    webproxysrvrTotalSocksSessions OBJECT-TYPE
        SYNTAX INTEGER
        ACCESS read-only
        STATUS mandatory
        DESCRIPTION
            "Total Socks Sessions is the accumulative number of Socks sessions serviced by the Web Proxy Server."
        ::= { web-Proxy-Server-Service 38 }

    webproxysrvrTotalSuccessfulSocksSessions OBJECT-TYPE
        SYNTAX INTEGER
        ACCESS read-only
        STATUS mandatory
        DESCRIPTION
            "Total Successful Socks Sessions is the accumulative number of Socks requests that were successfully serviced by the Web Proxy Server."
        ::= { web-Proxy-Server-Service 39 }

    webproxysrvrTotalFailedSocksSessions OBJECT-TYPE
        SYNTAX INTEGER
        ACCESS read-only
        STATUS mandatory
        DESCRIPTION
            "Total Failed Socks Sessions is the accumulative number of Socks requests that were were not serviced by the Web Proxy Server because the client did not have the access rights to satisfy the request, or an initial protocol error."
        ::= { web-Proxy-Server-Service 40 }

    webproxysrvrThreadPoolSize OBJECT-TYPE
        SYNTAX INTEGER
        ACCESS read-only
        STATUS mandatory
        DESCRIPTION
            "Thread Pool Size is the number of threads in the thread pool."
        ::= { web-Proxy-Server-Service 41 }

    webproxysrvrThreadPoolFailures OBJECT-TYPE
        SYNTAX INTEGER
        ACCESS read-only
        STATUS mandatory
        DESCRIPTION
            "Thread Pool Failures is the number of requests rejected because the thread pool was overcommitted."
        ::= { web-Proxy-Server-Service 42 }

    webproxysrvrSSLSessionsScavenged OBJECT-TYPE
        SYNTAX INTEGER
        ACCESS read-only
        STATUS mandatory
        DESCRIPTION
            "SSL sessions scavenged is the number of Secure Sockets Layer (SSL) sessions closed because of idle timeout and excessive SSL demand."
        ::= { web-Proxy-Server-Service 43 }

    webproxysrvrThreadPoolActiveSessions OBJECT-TYPE
        SYNTAX INTEGER
        ACCESS read-only
        STATUS mandatory
        DESCRIPTION
            "Thread Pool active sessions is the number of sessions being actively serviced by thread pool threads."
        ::= { web-Proxy-Server-Service 44 }

    webproxysrvrArrayBytesSentPerSec OBJECT-TYPE
        SYNTAX INTEGER
        ACCESS read-only
        STATUS mandatory
        DESCRIPTION
            "Array Bytes Sent/sec is the rate at which data bytes are sent by the Web Proxy Server to other proxies within the same array."
        ::= { web-Proxy-Server-Service 45 }

    webproxysrvrArrayBytesReceivedPerSec OBJECT-TYPE
        SYNTAX INTEGER
        ACCESS read-only
        STATUS mandatory
        DESCRIPTION
            "Array Bytes Received/sec is the rate at which data bytes are received by the Web Proxy Server from other Proxies within the same array in response to requests from this Proxy."
        ::= { web-Proxy-Server-Service 46 }

    webproxysrvrArrayBytesTotalPerSec OBJECT-TYPE
        SYNTAX INTEGER
        ACCESS read-only
        STATUS mandatory
        DESCRIPTION
            "Array Bytes Total/sec is the sum of Array Bytes Sent/sec and Bytes Received/sec. This is the total rate for all bytes transferred between the Proxy Server and other members of the same array."
        ::= { web-Proxy-Server-Service 47 }

    webproxysrvrTotalArrayFetches OBJECT-TYPE
        SYNTAX INTEGER
        ACCESS read-only
        STATUS mandatory
        DESCRIPTION
            "Total Array Fetches is the total number of requests that have been served by requesting the data from another Web Proxy Server within this array."
        ::= { web-Proxy-Server-Service 50 }

    webproxysrvrReverseBytesSentPerSec OBJECT-TYPE
        SYNTAX INTEGER
        ACCESS read-only
        STATUS mandatory
        DESCRIPTION
            "Reverse Bytes Sent/sec is the rate at which data bytes are sent by the Web Proxy Server to web publishing servers in response to Reverse Proxy requests."
        ::= { web-Proxy-Server-Service 51 }

    webproxysrvrReverseBytesReceivedPerSec OBJECT-TYPE
        SYNTAX INTEGER
        ACCESS read-only
        STATUS mandatory
        DESCRIPTION
            "Reverse Bytes Received/sec is the rate at which data bytes are received by the Web Proxy Server from web publishing serverse in response Reverse Proxy requests."
        ::= { web-Proxy-Server-Service 52 }

    webproxysrvrReverseBytesTotalPerSec OBJECT-TYPE
        SYNTAX INTEGER
        ACCESS read-only
        STATUS mandatory
        DESCRIPTION
            "Reverse Bytes Total/sec is the sum of Reverse Bytes Sent/sec and Bytes Received/sec. This is the total rate for all bytes transferred between the Proxy Server and web publishing servers in response to Reverse Proxy requests."
        ::= { web-Proxy-Server-Service 53 }

    webproxysrvrTotalReverseFetches OBJECT-TYPE
        SYNTAX INTEGER
        ACCESS read-only
        STATUS mandatory
        DESCRIPTION
            "Total Reverse Fetches is the total number of Reverse Proxy requests that have been served by requesting the data from web publishing servers."
        ::= { web-Proxy-Server-Service 54 }

    webproxysrvrRequestsPerSec OBJECT-TYPE
        SYNTAX Counter
        ACCESS read-only
        STATUS mandatory
        DESCRIPTION
            "Requests/sec is the rate of incoming requests that have been made to the Web Proxy Server."
        ::= { web-Proxy-Server-Service 55 }

    webproxysrvrFailingRequestsPerSec OBJECT-TYPE
        SYNTAX Counter
        ACCESS read-only
        STATUS mandatory
        DESCRIPTION
            "Failing Requests/sec is the rate of requests that have completed with some type of error."
        ::= { web-Proxy-Server-Service 56 }

    -- winSock Proxy Server MIB

    winSock-Proxy-Server OBJECT IDENTIFIER ::= { performance 28 }

    winsockproxysrvrSuccessfulDNSResolutions OBJECT-TYPE
        SYNTAX INTEGER
        ACCESS read-only
        STATUS mandatory
        DESCRIPTION
            "Number of 'gethostbyname' and 'gethostbyaddr' API calls successfully returned. These are calls used to resolve host DNS domain names and IP addresses for WinSock Proxy connections."
        ::= { winSock-Proxy-Server 1 }

    winsockproxysrvrFailedDNSResolutions OBJECT-TYPE
        SYNTAX INTEGER
        ACCESS read-only
        STATUS mandatory
        DESCRIPTION
            "Number of 'gethostbyname' and 'gethostbyaddr' API calls that have failed. These are calls used to resolve host DNS domain names and IP addresses for WinSock Proxy connections."
        ::= { winSock-Proxy-Server 2 }

    winsockproxysrvrPendingDNSResolutions OBJECT-TYPE
        SYNTAX INTEGER
        ACCESS read-only
        STATUS mandatory
        DESCRIPTION
            "Number of 'gethostbyname' and 'gethostbyaddr' API calls pending resolution. These are calls used to resolve host DNS domain names and IP addresses for WinSock Proxy connections."
        ::= { winSock-Proxy-Server 3 }

    winsockproxysrvrActiveSessions OBJECT-TYPE
        SYNTAX INTEGER
        ACCESS read-only
        STATUS mandatory
        DESCRIPTION
            "The number of active sessions for WinSock Proxy Server."
        ::= { winSock-Proxy-Server 4 }

    winsockproxysrvrActiveTCPConnections OBJECT-TYPE
        SYNTAX INTEGER
        ACCESS read-only
        STATUS mandatory
        DESCRIPTION
            "The total number of active TCP connections currently passing data. Connections pending or not yet established are counted elsewhere."
        ::= { winSock-Proxy-Server 5 }

    winsockproxysrvrActiveUDPConnections OBJECT-TYPE
        SYNTAX INTEGER
        ACCESS read-only
        STATUS mandatory
        DESCRIPTION
            "Total number of active UDP connections."
        ::= { winSock-Proxy-Server 6 }

    winsockproxysrvrConnectingTCPConnections OBJECT-TYPE
        SYNTAX INTEGER
        ACCESS read-only
        STATUS mandatory
        DESCRIPTION
            "Total number of TCP connections pending. These are connections awaiting completion between WinSock Proxy Server and remote computers."
        ::= { winSock-Proxy-Server 7 }

    winsockproxysrvrBack-ConnectingTCPConnections OBJECT-TYPE
        SYNTAX INTEGER
        ACCESS read-only
        STATUS mandatory
        DESCRIPTION
            "Total number of TCP connections awaiting an inbound 'connect' call to complete. These are connections placed by WinSock Proxy (WSP) to a client after WSP accepts a connection from the Internet on a listening socket."
        ::= { winSock-Proxy-Server 8 }

    winsockproxysrvrAcceptingTCPConnections OBJECT-TYPE
        SYNTAX INTEGER
        ACCESS read-only
        STATUS mandatory
        DESCRIPTION
            "Number of connection objects that wait for TCP connection from WinSock Proxy clients."
        ::= { winSock-Proxy-Server 9 }

    winsockproxysrvrListeningTCPConnections OBJECT-TYPE
        SYNTAX INTEGER
        ACCESS read-only
        STATUS mandatory
        DESCRIPTION
            "Number of connection objects that wait for TCP connections from remote Internet computers."
        ::= { winSock-Proxy-Server 10 }

    winsockproxysrvrWorkerThreads OBJECT-TYPE
        SYNTAX INTEGER
        ACCESS read-only
        STATUS mandatory
        DESCRIPTION
            "The number of WinSock Proxy worker threads that are currently alive."
        ::= { winSock-Proxy-Server 11 }

    winsockproxysrvrAvailableWorkerThreads OBJECT-TYPE
        SYNTAX INTEGER
        ACCESS read-only
        STATUS mandatory
        DESCRIPTION
            "The number of WinSock Proxy worker threads that are available (waiting in completion port queue)."
        ::= { winSock-Proxy-Server 12 }

    winsockproxysrvrBytesReadPerSec OBJECT-TYPE
        SYNTAX Counter
        ACCESS read-only
        STATUS mandatory
        DESCRIPTION
            "Number of bytes read by the data-pump per second."
        ::= { winSock-Proxy-Server 13 }

    winsockproxysrvrBytesWrittenPerSec OBJECT-TYPE
        SYNTAX Counter
        ACCESS read-only
        STATUS mandatory
        DESCRIPTION
            "Number of bytes written by data-pump per second."
        ::= { winSock-Proxy-Server 14 }

    winsockproxysrvrNon-connectedUDPMappings OBJECT-TYPE
        SYNTAX INTEGER
        ACCESS read-only
        STATUS mandatory
        DESCRIPTION
            "The number of mappings available for UDP connections."
        ::= { winSock-Proxy-Server 15 }

    winsockproxysrvrDNSCacheEntries OBJECT-TYPE
        SYNTAX INTEGER
        ACCESS read-only
        STATUS mandatory
        DESCRIPTION
            "DNS Cache Entries is the current number of DNS domain name entries cached by the Web Proxy Server."
        ::= { winSock-Proxy-Server 16 }

    winsockproxysrvrDNSCacheHits OBJECT-TYPE
        SYNTAX INTEGER
        ACCESS read-only
        STATUS mandatory
        DESCRIPTION
            "DNS Cache Hits is the total number of times a DNS domain name was found within the DNS Cache."
        ::= { winSock-Proxy-Server 17 }

    winsockproxysrvrDNSCacheFlushes OBJECT-TYPE
        SYNTAX INTEGER
        ACCESS read-only
        STATUS mandatory
        DESCRIPTION
            "DNS Cache Flushes is the total number of times that the DNS domain name cache has been flushed or cleared by the Web Proxy Server."
        ::= { winSock-Proxy-Server 18 }

    winsockproxysrvrDNSRetrievals OBJECT-TYPE
        SYNTAX INTEGER
        ACCESS read-only
        STATUS mandatory
        DESCRIPTION
            "DNS Retrievals is the total number of DNS domain names that have been retrieved by the Web Proxy Server."
        ::= { winSock-Proxy-Server 19 }

    winsockproxysrvrDNSCacheHitsPercent OBJECT-TYPE
        SYNTAX INTEGER
        ACCESS read-only
        STATUS mandatory
        DESCRIPTION
            "DNS Cache Hits % is the percentage of DNS domain names served from the Web Proxy Server cache, from the total of all DNS entries that have been retrieved by the Web Proxy Server."
        ::= { winSock-Proxy-Server 20 }

    -- web Proxy Server Cache MIB

    web-Proxy-Server-Cache OBJECT IDENTIFIER ::= { performance 29 }

    webproxysrvrcacheURLsInCache OBJECT-TYPE
        SYNTAX Counter
        ACCESS read-only
        STATUS mandatory
        DESCRIPTION
            "URLs in Cache is the current number of URLs in the URL Cache."
        ::= { web-Proxy-Server-Cache 1 }

    webproxysrvrcacheBytesInCache OBJECT-TYPE
        SYNTAX Counter
        ACCESS read-only
        STATUS mandatory
        DESCRIPTION
            "Bytes in Cache is the total number of bytes currently contained in the URL Cache."
        ::= { web-Proxy-Server-Cache 2 }

    webproxysrvrcacheTotalBytesCached OBJECT-TYPE
        SYNTAX Counter
        ACCESS read-only
        STATUS mandatory
        DESCRIPTION
            "Total Bytes Cached is the cumulative number of bytes that have been placed into the URL Cache."
        ::= { web-Proxy-Server-Cache 3 }

    webproxysrvrcacheTotalBytesRetrieved OBJECT-TYPE
        SYNTAX Counter
        ACCESS read-only
        STATUS mandatory
        DESCRIPTION
            "Total Bytes Retrieved is the cumulative number of bytes that have been retrieved from the URL Cache."
        ::= { web-Proxy-Server-Cache 4 }

    webproxysrvrcacheTotalURLsCached OBJECT-TYPE
        SYNTAX Counter
        ACCESS read-only
        STATUS mandatory
        DESCRIPTION
            "Total URLs Cached is the cumulative number of URLs that have been stored into the URL Cache."
        ::= { web-Proxy-Server-Cache 5 }

    webproxysrvrcacheTotalURLsRetrieved OBJECT-TYPE
        SYNTAX Counter
        ACCESS read-only
        STATUS mandatory
        DESCRIPTION
            "Total URLs Retrieved is the cumulative number of URLs that have been retrieved from the URL Cache."
        ::= { web-Proxy-Server-Cache 6 }

    webproxysrvrcacheMaxBytesCached OBJECT-TYPE
        SYNTAX Counter
        ACCESS read-only
        STATUS mandatory
        DESCRIPTION
            "Max Bytes Cached is the maximum number of bytes that have been stored in the URL Cache."
        ::= { web-Proxy-Server-Cache 7 }

    webproxysrvrcacheMaxURLsCached OBJECT-TYPE
        SYNTAX Counter
        ACCESS read-only
        STATUS mandatory
        DESCRIPTION
            "Max URLs Cached is the maximum number of URLs that have been stored in the URL Cache."
        ::= { web-Proxy-Server-Cache 8 }

    webproxysrvrcacheTotalActivelyRefreshedURLs OBJECT-TYPE
        SYNTAX Counter
        ACCESS read-only
        STATUS mandatory
        DESCRIPTION
            "Total Actively Refreshed URLs is the cumulative number of popular URLs in the URL cache that have been preemptively refreshed from the Internet."
        ::= { web-Proxy-Server-Cache 9 }

    webproxysrvrcacheTotalBytesActivelyRefreshed OBJECT-TYPE
        SYNTAX Counter
        ACCESS read-only
        STATUS mandatory
        DESCRIPTION
            "Total Bytes Actively Refreshed is the total of bytes that have been retrieved from the Internet to preemptively refresh popular URLs in the URL cache."
        ::= { web-Proxy-Server-Cache 10 }

    webproxysrvrcacheURLRetrieveRate OBJECT-TYPE
        SYNTAX Counter
        ACCESS read-only
        STATUS mandatory
        DESCRIPTION
            "URL Retrieve Rate is the rate at which URLs are retrieved from the URL cache."
        ::= { web-Proxy-Server-Cache 11 }

    webproxysrvrcacheBytesRetrievedRate OBJECT-TYPE
        SYNTAX Counter
        ACCESS read-only
        STATUS mandatory
        DESCRIPTION
            "Bytes Retrieved Rate is the rate at which bytes of data are retrieved from the URL cache."
        ::= { web-Proxy-Server-Cache 12 }

    webproxysrvrcacheURLCommitRate OBJECT-TYPE
        SYNTAX Counter
        ACCESS read-only
        STATUS mandatory
        DESCRIPTION
            "URL Commit Rate is the rate at which URLs are commited to the URL cache."
        ::= { web-Proxy-Server-Cache 13 }

    webproxysrvrcacheBytesCommitedRate OBJECT-TYPE
        SYNTAX Counter
        ACCESS read-only
        STATUS mandatory
        DESCRIPTION
            "Bytes Commited Rate is the rate at which bytes of data are commited to the URL cache."
        ::= { web-Proxy-Server-Cache 14 }

    webproxysrvrcacheActiveURLRefreshRate OBJECT-TYPE
        SYNTAX Counter
        ACCESS read-only
        STATUS mandatory
        DESCRIPTION
            "Active URL Refresh Rate is the rate at which popular URLs in the URL cache are preemptively refreshed from the Internet."
        ::= { web-Proxy-Server-Cache 15 }

    webproxysrvrcacheActiveRefreshBytesRate OBJECT-TYPE
        SYNTAX Counter
        ACCESS read-only
        STATUS mandatory
        DESCRIPTION
            "Active Refresh Bytes Rate is the rate at which bytes of data are retrieved from the Internet to preemptively refresh popular URLs in the URL cache."
        ::= { web-Proxy-Server-Cache 16 }

    -- telephony MIB

    telephony OBJECT IDENTIFIER ::= { performance 30 }

    telephonyLines OBJECT-TYPE
        SYNTAX INTEGER
        ACCESS read-only
        STATUS mandatory
        DESCRIPTION
            "The number of telephone lines serviced by this computer."
        ::= { telephony 1 }

    telephonyTelephoneDevices OBJECT-TYPE
        SYNTAX INTEGER
        ACCESS read-only
        STATUS mandatory
        DESCRIPTION
            "The number of telephone devices serviced by this computer."
        ::= { telephony 2 }

    telephonyActiveLines OBJECT-TYPE
        SYNTAX INTEGER
        ACCESS read-only
        STATUS mandatory
        DESCRIPTION
            "The number of telephone lines serviced by this computer that are currently active."
        ::= { telephony 3 }

    telephonyActiveTelephones OBJECT-TYPE
        SYNTAX INTEGER
        ACCESS read-only
        STATUS mandatory
        DESCRIPTION
            "The number of telephone devices that are currently being monitored."
        ::= { telephony 4 }

    telephonyOutgoingCallsPerSec OBJECT-TYPE
        SYNTAX Counter
        ACCESS read-only
        STATUS mandatory
        DESCRIPTION
            "The rate of outgoing calls made by this computer."
        ::= { telephony 5 }

    telephonyIncomingCallsPerSec OBJECT-TYPE
        SYNTAX Counter
        ACCESS read-only
        STATUS mandatory
        DESCRIPTION
            "The rate of incoming calls answered by this computer."
        ::= { telephony 6 }

    telephonyClientApps OBJECT-TYPE
        SYNTAX INTEGER
        ACCESS read-only
        STATUS mandatory
        DESCRIPTION
            "The number of applications that are currently using telephony services."
        ::= { telephony 7 }

    telephonyCurrentOutgoingCalls OBJECT-TYPE
        SYNTAX INTEGER
        ACCESS read-only
        STATUS mandatory
        DESCRIPTION
            "Current outgoing calls being serviced by this computer."
        ::= { telephony 8 }

    telephonyCurrentIncomingCalls OBJECT-TYPE
        SYNTAX INTEGER
        ACCESS read-only
        STATUS mandatory
        DESCRIPTION
            "Current incoming calls being serviced by this computer."
        ::= { telephony 9 }

    -- rAS Port MIB

    rasportrAS-PortTable OBJECT-TYPE
        SYNTAX SEQUENCE OF rasportrAS-PortEntry
        ACCESS not-accessible
        STATUS mandatory
        DESCRIPTION
            "A table containing performance information for instances of 'rAS-Port' objects."
        ::= { performance 31 }

    rasportrAS-PortEntry OBJECT-TYPE
        SYNTAX rasportrAS-PortEntry
        ACCESS not-accessible
        STATUS mandatory
        DESCRIPTION
            "Performance information for one particular instance of 'rAS-Port' object."
        INDEX { rasportrAS-PortIndex }
        ::= { rasportrAS-PortTable 1 }

    rasportrAS-PortEntry ::=
        SEQUENCE {
            rasportrAS-PortIndex INTEGER,
            rasportrAS-PortInstance DisplayString,
            rasportBytesTransmitted INTEGER,
            rasportBytesReceived INTEGER,
            rasportFramesTransmitted INTEGER,
            rasportFramesReceived INTEGER,
            rasportPercentCompressionOut INTEGER,
            rasportPercentCompressionIn INTEGER,
            rasportCRCErrors INTEGER,
            rasportTimeoutErrors INTEGER,
            rasportSerialOverrunErrors INTEGER,
            rasportAlignmentErrors INTEGER,
            rasportBufferOverrunErrors INTEGER,
            rasportTotalErrors INTEGER,
            rasportBytesTransmittedPerSec Counter,
            rasportBytesReceivedPerSec Counter,
            rasportFramesTransmittedPerSec Counter,
            rasportFramesReceivedPerSec Counter,
            rasportTotalErrorsPerSec Counter
        }

    rasportrAS-PortIndex OBJECT-TYPE
        SYNTAX INTEGER
        ACCESS read-only
        STATUS mandatory
        DESCRIPTION
            "Index."
        ::= { rasportrAS-PortEntry 1 }

    rasportrAS-PortInstance OBJECT-TYPE
        SYNTAX DisplayString
        ACCESS read-only
        STATUS mandatory
        DESCRIPTION
            "Instance name."
        ::= { rasportrAS-PortEntry 2 }

    rasportBytesTransmitted OBJECT-TYPE
        SYNTAX INTEGER
        ACCESS read-only
        STATUS mandatory
        DESCRIPTION
            "The number of bytes transmitted total for this connection."
        ::= { rasportrAS-PortEntry 3 }

    rasportBytesReceived OBJECT-TYPE
        SYNTAX INTEGER
        ACCESS read-only
        STATUS mandatory
        DESCRIPTION
            "The number of bytes received total for this connection."
        ::= { rasportrAS-PortEntry 4 }

    rasportFramesTransmitted OBJECT-TYPE
        SYNTAX INTEGER
        ACCESS read-only
        STATUS mandatory
        DESCRIPTION
            "The number of data frames transmitted total for this connection."
        ::= { rasportrAS-PortEntry 5 }

    rasportFramesReceived OBJECT-TYPE
        SYNTAX INTEGER
        ACCESS read-only
        STATUS mandatory
        DESCRIPTION
            "The number of data frames received total for this connection."
        ::= { rasportrAS-PortEntry 6 }

    rasportPercentCompressionOut OBJECT-TYPE
        SYNTAX INTEGER
        ACCESS read-only
        STATUS mandatory
        DESCRIPTION
            "The compression ratio for bytes being transmitted."
        ::= { rasportrAS-PortEntry 7 }

    rasportPercentCompressionIn OBJECT-TYPE
        SYNTAX INTEGER
        ACCESS read-only
        STATUS mandatory
        DESCRIPTION
            "The compression ratio for bytes being received."
        ::= { rasportrAS-PortEntry 8 }

    rasportCRCErrors OBJECT-TYPE
        SYNTAX INTEGER
        ACCESS read-only
        STATUS mandatory
        DESCRIPTION
            "The total number of CRC Errors for this connection.  CRC Errors occur when the frame received contains erroneous data."
        ::= { rasportrAS-PortEntry 9 }

    rasportTimeoutErrors OBJECT-TYPE
        SYNTAX INTEGER
        ACCESS read-only
        STATUS mandatory
        DESCRIPTION
            "The total number of Timeout Errors for this connection.  Timeout Errors occur when an expected is not received in time."
        ::= { rasportrAS-PortEntry 10 }

    rasportSerialOverrunErrors OBJECT-TYPE
        SYNTAX INTEGER
        ACCESS read-only
        STATUS mandatory
        DESCRIPTION
            "The total number of Serial Overrun Errors for this connection.  Serial Overrun Errors occur when the hardware cannot handle the rate at which data is received."
        ::= { rasportrAS-PortEntry 11 }

    rasportAlignmentErrors OBJECT-TYPE
        SYNTAX INTEGER
        ACCESS read-only
        STATUS mandatory
        DESCRIPTION
            "The total number of Alignment Errors for this connection.  Alignment Errors occur when a byte received is different from the byte expected."
        ::= { rasportrAS-PortEntry 12 }

    rasportBufferOverrunErrors OBJECT-TYPE
        SYNTAX INTEGER
        ACCESS read-only
        STATUS mandatory
        DESCRIPTION
            "The total number of Buffer Overrun Errors for this connection.  Buffer Overrun Errors when the software cannot handle the rate at which data is received."
        ::= { rasportrAS-PortEntry 13 }

    rasportTotalErrors OBJECT-TYPE
        SYNTAX INTEGER
        ACCESS read-only
        STATUS mandatory
        DESCRIPTION
            "The total number of CRC, Timeout, Serial Overrun, Alignment, and Buffer Overrun Errors for this connection."
        ::= { rasportrAS-PortEntry 14 }

    rasportBytesTransmittedPerSec OBJECT-TYPE
        SYNTAX Counter
        ACCESS read-only
        STATUS mandatory
        DESCRIPTION
            "The number of bytes transmitted per second."
        ::= { rasportrAS-PortEntry 15 }

    rasportBytesReceivedPerSec OBJECT-TYPE
        SYNTAX Counter
        ACCESS read-only
        STATUS mandatory
        DESCRIPTION
            "The number of bytes received per second."
        ::= { rasportrAS-PortEntry 16 }

    rasportFramesTransmittedPerSec OBJECT-TYPE
        SYNTAX Counter
        ACCESS read-only
        STATUS mandatory
        DESCRIPTION
            "The number of frames transmitted per second."
        ::= { rasportrAS-PortEntry 17 }

    rasportFramesReceivedPerSec OBJECT-TYPE
        SYNTAX Counter
        ACCESS read-only
        STATUS mandatory
        DESCRIPTION
            "The number of frames received per second."
        ::= { rasportrAS-PortEntry 18 }

    rasportTotalErrorsPerSec OBJECT-TYPE
        SYNTAX Counter
        ACCESS read-only
        STATUS mandatory
        DESCRIPTION
            "The total number of CRC, Timeout, Serial Overrun, Alignment, and Buffer Overrun Errors per second."
        ::= { rasportrAS-PortEntry 19 }

    -- nWLink NetBIOS MIB

    nwnetbiosnWLink-NetBIOSTable OBJECT-TYPE
        SYNTAX SEQUENCE OF nwnetbiosnWLink-NetBIOSEntry
        ACCESS not-accessible
        STATUS mandatory
        DESCRIPTION
            "A table containing performance information for instances of 'nWLink-NetBIOS' objects."
        ::= { performance 32 }

    nwnetbiosnWLink-NetBIOSEntry OBJECT-TYPE
        SYNTAX nwnetbiosnWLink-NetBIOSEntry
        ACCESS not-accessible
        STATUS mandatory
        DESCRIPTION
            "Performance information for one particular instance of 'nWLink-NetBIOS' object."
        INDEX { nwnetbiosnWLink-NetBIOSIndex }
        ::= { nwnetbiosnWLink-NetBIOSTable 1 }

    nwnetbiosnWLink-NetBIOSEntry ::=
        SEQUENCE {
            nwnetbiosnWLink-NetBIOSIndex INTEGER,
            nwnetbiosnWLink-NetBIOSInstance DisplayString,
            nwnetbiosDatagramsPerSec Counter,
            nwnetbiosDatagramBytesPerSec INTEGER,
            nwnetbiosPacketsPerSec Counter,
            nwnetbiosFramesPerSec Counter,
            nwnetbiosFrameBytesPerSec INTEGER,
            nwnetbiosBytesTotalPerSec INTEGER,
            nwnetbiosConnectionsOpen INTEGER,
            nwnetbiosConnectionsNoRetries INTEGER,
            nwnetbiosConnectionsWithRetries INTEGER,
            nwnetbiosDisconnectsLocal INTEGER,
            nwnetbiosDisconnectsRemote INTEGER,
            nwnetbiosFailuresLink INTEGER,
            nwnetbiosFailuresAdapter INTEGER,
            nwnetbiosConnectionSessionTimeouts INTEGER,
            nwnetbiosConnectionsCanceled INTEGER,
            nwnetbiosFailuresResourceRemote INTEGER,
            nwnetbiosFailuresResourceLocal INTEGER,
            nwnetbiosFailuresNotFound INTEGER,
            nwnetbiosFailuresNoListen INTEGER,
            nwnetbiosDatagramsSentPerSec Counter,
            nwnetbiosDatagramBytesSentPerSec INTEGER,
            nwnetbiosDatagramsReceivedPerSec Counter,
            nwnetbiosDatagramBytesReceivedPerSec INTEGER,
            nwnetbiosPacketsSentPerSec Counter,
            nwnetbiosPacketsReceivedPerSec Counter,
            nwnetbiosFramesSentPerSec Counter,
            nwnetbiosFrameBytesSentPerSec INTEGER,
            nwnetbiosFramesReceivedPerSec Counter,
            nwnetbiosFrameBytesReceivedPerSec INTEGER,
            nwnetbiosFramesRe-SentPerSec Counter,
            nwnetbiosFrameBytesRe-SentPerSec INTEGER,
            nwnetbiosFramesRejectedPerSec Counter,
            nwnetbiosFrameBytesRejectedPerSec INTEGER,
            nwnetbiosExpirationsResponse INTEGER,
            nwnetbiosExpirationsAck INTEGER,
            nwnetbiosWindowSendMaximum INTEGER,
            nwnetbiosWindowSendAverage INTEGER,
            nwnetbiosPiggybackAckQueuedPerSec Counter,
            nwnetbiosPiggybackAckTimeouts INTEGER
        }

    nwnetbiosnWLink-NetBIOSIndex OBJECT-TYPE
        SYNTAX INTEGER
        ACCESS read-only
        STATUS mandatory
        DESCRIPTION
            "Index."
        ::= { nwnetbiosnWLink-NetBIOSEntry 1 }

    nwnetbiosnWLink-NetBIOSInstance OBJECT-TYPE
        SYNTAX DisplayString
        ACCESS read-only
        STATUS mandatory
        DESCRIPTION
            "Instance name."
        ::= { nwnetbiosnWLink-NetBIOSEntry 2 }

    nwnetbiosDatagramsPerSec OBJECT-TYPE
        SYNTAX Counter
        ACCESS read-only
        STATUS mandatory
        DESCRIPTION
            "Datagrams/sec is the rate that datagrams are processed by the computer.  This counter displays the sum of datagrams sent and datagrams received.  A datagram is a connectionless packet whose delivery to a remote is not guaranteed."
        ::= { nwnetbiosnWLink-NetBIOSEntry 3 }

    nwnetbiosDatagramBytesPerSec OBJECT-TYPE
        SYNTAX INTEGER
        ACCESS read-only
        STATUS mandatory
        DESCRIPTION
            "Datagram Bytes/sec is the rate that datagram bytes are processed by the computer.  This counter is the sum of datagram bytes that are sent as well as received.  A datagram is a connectionless packet whose delivery to a remote is not guaranteed."
        ::= { nwnetbiosnWLink-NetBIOSEntry 4 }

    nwnetbiosPacketsPerSec OBJECT-TYPE
        SYNTAX Counter
        ACCESS read-only
        STATUS mandatory
        DESCRIPTION
            "Packets/sec is the rate that packets are processed by the computer.  This count is the sum of Packets Sent and Packets Received per second.  This counter includes all packets processed: control as well as data packets."
        ::= { nwnetbiosnWLink-NetBIOSEntry 5 }

    nwnetbiosFramesPerSec OBJECT-TYPE
        SYNTAX Counter
        ACCESS read-only
        STATUS mandatory
        DESCRIPTION
            "Frames/sec is the rate that data frames (or packets) are processed by the computer.  This counter is the sum of data frames sent and data frames received.  This counter only counts those frames (packets) that carry data."
        ::= { nwnetbiosnWLink-NetBIOSEntry 6 }

    nwnetbiosFrameBytesPerSec OBJECT-TYPE
        SYNTAX INTEGER
        ACCESS read-only
        STATUS mandatory
        DESCRIPTION
            "Frame Bytes/sec is the rate that data bytes are processed by the computer.  This counter is the sum of data frame bytes sent and received.  This counter only counts the byte in frames (packets) that carry data."
        ::= { nwnetbiosnWLink-NetBIOSEntry 7 }

    nwnetbiosBytesTotalPerSec OBJECT-TYPE
        SYNTAX INTEGER
        ACCESS read-only
        STATUS mandatory
        DESCRIPTION
            "Bytes Total/sec is the sum of Frame Bytes/sec and Datagram Bytes/sec.  This is the total rate of bytes sent to or received from the network by the protocol, but only counts the bytes in frames (i.e., packets) which carry data."
        ::= { nwnetbiosnWLink-NetBIOSEntry 8 }

    nwnetbiosConnectionsOpen OBJECT-TYPE
        SYNTAX INTEGER
        ACCESS read-only
        STATUS mandatory
        DESCRIPTION
            "Connections Open is the number of connections currently open for this protocol.  This counter shows the current count only and does not accumulate over time."
        ::= { nwnetbiosnWLink-NetBIOSEntry 9 }

    nwnetbiosConnectionsNoRetries OBJECT-TYPE
        SYNTAX INTEGER
        ACCESS read-only
        STATUS mandatory
        DESCRIPTION
            "Connections No Retries is the total count of connections that were successfully made on the first try.  This number is an accumulator and shows a running total."
        ::= { nwnetbiosnWLink-NetBIOSEntry 10 }

    nwnetbiosConnectionsWithRetries OBJECT-TYPE
        SYNTAX INTEGER
        ACCESS read-only
        STATUS mandatory
        DESCRIPTION
            "Connections With Retries is the total count of connections that were made after retrying the attempt.  A retry occurs when the first connection attempt failed.  This number is an accumulator and shows a running total."
        ::= { nwnetbiosnWLink-NetBIOSEntry 11 }

    nwnetbiosDisconnectsLocal OBJECT-TYPE
        SYNTAX INTEGER
        ACCESS read-only
        STATUS mandatory
        DESCRIPTION
            "Disconnects Local is the number of session disconnections that were initiated by the local computer.  This number is an accumulator and shows a running total."
        ::= { nwnetbiosnWLink-NetBIOSEntry 12 }

    nwnetbiosDisconnectsRemote OBJECT-TYPE
        SYNTAX INTEGER
        ACCESS read-only
        STATUS mandatory
        DESCRIPTION
            "Disconnects Remote is the number of session disconnections that were initiated by the remote computer.  This number is an accumulator and shows a running total."
        ::= { nwnetbiosnWLink-NetBIOSEntry 13 }

    nwnetbiosFailuresLink OBJECT-TYPE
        SYNTAX INTEGER
        ACCESS read-only
        STATUS mandatory
        DESCRIPTION
            "Failures Link is the number of connections that were dropped due to a link failure.  This number is an accumulator and shows a running total."
        ::= { nwnetbiosnWLink-NetBIOSEntry 14 }

    nwnetbiosFailuresAdapter OBJECT-TYPE
        SYNTAX INTEGER
        ACCESS read-only
        STATUS mandatory
        DESCRIPTION
            "Failures Adapter is the number of connections that were dropped due to an adapter failure.  This number is an accumulator and shows a running total."
        ::= { nwnetbiosnWLink-NetBIOSEntry 15 }

    nwnetbiosConnectionSessionTimeouts OBJECT-TYPE
        SYNTAX INTEGER
        ACCESS read-only
        STATUS mandatory
        DESCRIPTION
            "Connection Session Timeouts is the number of connections that were dropped due to a session timeout.  This number is an accumulator and shows a running total."
        ::= { nwnetbiosnWLink-NetBIOSEntry 16 }

    nwnetbiosConnectionsCanceled OBJECT-TYPE
        SYNTAX INTEGER
        ACCESS read-only
        STATUS mandatory
        DESCRIPTION
            "Connections Canceled is the number of connections that were canceled.  This number is an accumulator and shows a running total."
        ::= { nwnetbiosnWLink-NetBIOSEntry 17 }

    nwnetbiosFailuresResourceRemote OBJECT-TYPE
        SYNTAX INTEGER
        ACCESS read-only
        STATUS mandatory
        DESCRIPTION
            "Failures Resource Remote is the number of connections that failed because of resource problems or shortages on the remote computer.  This number is an accumulator and shows a running total."
        ::= { nwnetbiosnWLink-NetBIOSEntry 18 }

    nwnetbiosFailuresResourceLocal OBJECT-TYPE
        SYNTAX INTEGER
        ACCESS read-only
        STATUS mandatory
        DESCRIPTION
            "Failures Resource Local is the number of connections that failed because of resource problems or shortages on the local computer.  This number is an accumulator and shows a running total."
        ::= { nwnetbiosnWLink-NetBIOSEntry 19 }

    nwnetbiosFailuresNotFound OBJECT-TYPE
        SYNTAX INTEGER
        ACCESS read-only
        STATUS mandatory
        DESCRIPTION
            "Failures Not Found is the number of connection attempts that failed because the remote computer could not be found.  This number is an accumulator and shows a running total."
        ::= { nwnetbiosnWLink-NetBIOSEntry 20 }

    nwnetbiosFailuresNoListen OBJECT-TYPE
        SYNTAX INTEGER
        ACCESS read-only
        STATUS mandatory
        DESCRIPTION
            "Failures No Listen is the number of connections that were rejected because the remote computer was not listening for connection requests."
        ::= { nwnetbiosnWLink-NetBIOSEntry 21 }

    nwnetbiosDatagramsSentPerSec OBJECT-TYPE
        SYNTAX Counter
        ACCESS read-only
        STATUS mandatory
        DESCRIPTION
            "Datagrams Sent/sec is the rate that datagrams are sent from the computer.  A datagram is a connectionless packet whose delivery to a remote computer is not guaranteed."
        ::= { nwnetbiosnWLink-NetBIOSEntry 22 }

    nwnetbiosDatagramBytesSentPerSec OBJECT-TYPE
        SYNTAX INTEGER
        ACCESS read-only
        STATUS mandatory
        DESCRIPTION
            "Datagram Bytes Sent/sec is the rate that datagram bytes are sent from the computer.  A datagram is a connectionless packet whose delivery to a remote computer is not guaranteed."
        ::= { nwnetbiosnWLink-NetBIOSEntry 23 }

    nwnetbiosDatagramsReceivedPerSec OBJECT-TYPE
        SYNTAX Counter
        ACCESS read-only
        STATUS mandatory
        DESCRIPTION
            "Datagrams Received/sec is the rate that datagrams are received by the computer.  A datagram is a connectionless packet whose delivery to a remote computer is not guaranteed."
        ::= { nwnetbiosnWLink-NetBIOSEntry 24 }

    nwnetbiosDatagramBytesReceivedPerSec OBJECT-TYPE
        SYNTAX INTEGER
        ACCESS read-only
        STATUS mandatory
        DESCRIPTION
            "Datagram Bytes Received/sec is the rate that datagram bytes are received by the computer.  A datagram is a connectionless packet whose delivery to a remote computer is not guaranteed."
        ::= { nwnetbiosnWLink-NetBIOSEntry 25 }

    nwnetbiosPacketsSentPerSec OBJECT-TYPE
        SYNTAX Counter
        ACCESS read-only
        STATUS mandatory
        DESCRIPTION
            "Packets Sent/sec is the rate that packets are sent by the computer.  This counter counts all packets sent by the computer, i.e. control as well as data packets."
        ::= { nwnetbiosnWLink-NetBIOSEntry 26 }

    nwnetbiosPacketsReceivedPerSec OBJECT-TYPE
        SYNTAX Counter
        ACCESS read-only
        STATUS mandatory
        DESCRIPTION
            "Packets Received/sec is the rate that packets are received by the computer.  This counter counts all packets processed: control as well as data packets."
        ::= { nwnetbiosnWLink-NetBIOSEntry 27 }

    nwnetbiosFramesSentPerSec OBJECT-TYPE
        SYNTAX Counter
        ACCESS read-only
        STATUS mandatory
        DESCRIPTION
            "Frames Sent/sec is the rate that data frames are sent by the computer.  This counter only counts the frames (packets) that carry data."
        ::= { nwnetbiosnWLink-NetBIOSEntry 28 }

    nwnetbiosFrameBytesSentPerSec OBJECT-TYPE
        SYNTAX INTEGER
        ACCESS read-only
        STATUS mandatory
        DESCRIPTION
            "Frame Bytes Sent/sec is the rate that data bytes are sent by the computer.  This counter only counts the bytes in frames (packets) that carry data."
        ::= { nwnetbiosnWLink-NetBIOSEntry 29 }

    nwnetbiosFramesReceivedPerSec OBJECT-TYPE
        SYNTAX Counter
        ACCESS read-only
        STATUS mandatory
        DESCRIPTION
            "Frames Received/sec is the rate that data frames are received by the computer.  This counter only counts the frames (packets) that carry data."
        ::= { nwnetbiosnWLink-NetBIOSEntry 30 }

    nwnetbiosFrameBytesReceivedPerSec OBJECT-TYPE
        SYNTAX INTEGER
        ACCESS read-only
        STATUS mandatory
        DESCRIPTION
            "Frame Bytes Received/sec is the rate that data bytes are received by the computer.  This counter only counts the frames (packets) that carry data."
        ::= { nwnetbiosnWLink-NetBIOSEntry 31 }

    nwnetbiosFramesRe-SentPerSec OBJECT-TYPE
        SYNTAX Counter
        ACCESS read-only
        STATUS mandatory
        DESCRIPTION
            "Frames Re-Sent/sec is the rate that data frames (packets) are re-sent by the computer.  This counter only counts the frames or packets that carry data."
        ::= { nwnetbiosnWLink-NetBIOSEntry 32 }

    nwnetbiosFrameBytesRe-SentPerSec OBJECT-TYPE
        SYNTAX INTEGER
        ACCESS read-only
        STATUS mandatory
        DESCRIPTION
            "Frame Bytes Re-Sent/sec is the rate that data bytes are re-sent by the computer.  This counter only counts the bytes in frames that carry data."
        ::= { nwnetbiosnWLink-NetBIOSEntry 33 }

    nwnetbiosFramesRejectedPerSec OBJECT-TYPE
        SYNTAX Counter
        ACCESS read-only
        STATUS mandatory
        DESCRIPTION
            "Frames Rejected/sec is the rate that data frames are rejected.  This counter only counts the frames (packets) that carry data."
        ::= { nwnetbiosnWLink-NetBIOSEntry 34 }

    nwnetbiosFrameBytesRejectedPerSec OBJECT-TYPE
        SYNTAX INTEGER
        ACCESS read-only
        STATUS mandatory
        DESCRIPTION
            "Frame Bytes Rejected/sec is the rate that data bytes are rejected.  This counter only counts the bytes in data frames (packets) that carry data."
        ::= { nwnetbiosnWLink-NetBIOSEntry 35 }

    nwnetbiosExpirationsResponse OBJECT-TYPE
        SYNTAX INTEGER
        ACCESS read-only
        STATUS mandatory
        DESCRIPTION
            "Expirations Response is the count of T1 timer expirations."
        ::= { nwnetbiosnWLink-NetBIOSEntry 36 }

    nwnetbiosExpirationsAck OBJECT-TYPE
        SYNTAX INTEGER
        ACCESS read-only
        STATUS mandatory
        DESCRIPTION
            "Expirations Ack is the count of T2 timer expirations"
        ::= { nwnetbiosnWLink-NetBIOSEntry 37 }

    nwnetbiosWindowSendMaximum OBJECT-TYPE
        SYNTAX INTEGER
        ACCESS read-only
        STATUS mandatory
        DESCRIPTION
            "Window Send Maximum is the maximum number of bytes of data that will be sent before waiting for an acknowledgment from the remote computer."
        ::= { nwnetbiosnWLink-NetBIOSEntry 38 }

    nwnetbiosWindowSendAverage OBJECT-TYPE
        SYNTAX INTEGER
        ACCESS read-only
        STATUS mandatory
        DESCRIPTION
            "Window Send Average is the running average number of data bytes that were sent before waiting for an acknowledgment from the remote computer."
        ::= { nwnetbiosnWLink-NetBIOSEntry 39 }

    nwnetbiosPiggybackAckQueuedPerSec OBJECT-TYPE
        SYNTAX Counter
        ACCESS read-only
        STATUS mandatory
        DESCRIPTION
            "Piggyback Ack Queued/sec is the rate that piggybacked acknowledgments are queued. Piggyback acknowledgments are acknowledgments to received packets that are to be included in the next outgoing packet to the remote computer."
        ::= { nwnetbiosnWLink-NetBIOSEntry 40 }

    nwnetbiosPiggybackAckTimeouts OBJECT-TYPE
        SYNTAX INTEGER
        ACCESS read-only
        STATUS mandatory
        DESCRIPTION
            "Piggyback Ack Timeouts is the number of times that a piggyback acknowledgment could not be sent because there was no outgoing packet to the remote on which to piggyback.  A piggyback ack is an acknowledgment to a received packet that is sent along in an outgoing data packet to the remote computer.  If no outgoing packet is sent within the timeout period, then an ack packet is sent and this counter is incremented."
        ::= { nwnetbiosnWLink-NetBIOSEntry 41 }

    -- system MIB

    ntsystem OBJECT IDENTIFIER ::= { performance 33 }

    ntsystemFileReadOperationsPerSec OBJECT-TYPE
        SYNTAX Counter
        ACCESS read-only
        STATUS mandatory
        DESCRIPTION
            "File Read Operations/sec is an aggregate of all the file system read operations on the computer."
        ::= { ntsystem 1 }

    ntsystemFileWriteOperationsPerSec OBJECT-TYPE
        SYNTAX Counter
        ACCESS read-only
        STATUS mandatory
        DESCRIPTION
            "File Write Operations/sec is an aggregate of all the file system write operations on the computer."
        ::= { ntsystem 2 }

    ntsystemFileControlOperationsPerSec OBJECT-TYPE
        SYNTAX Counter
        ACCESS read-only
        STATUS mandatory
        DESCRIPTION
            "File Control Operations/sec is an aggregate of all file system operations that are neither reads nor writes.  These operations usually include file system control requests or requests for information about device characteristics or status."
        ::= { ntsystem 3 }

    ntsystemFileReadBytesPerSec OBJECT-TYPE
        SYNTAX INTEGER
        ACCESS read-only
        STATUS mandatory
        DESCRIPTION
            "File Read Bytes/sec is an aggregate of the bytes transferred for all the file system read operations on the computer."
        ::= { ntsystem 4 }

    ntsystemFileWriteBytesPerSec OBJECT-TYPE
        SYNTAX INTEGER
        ACCESS read-only
        STATUS mandatory
        DESCRIPTION
            "File Write Bytes/sec is an aggregate of the bytes transferred for all the file system write operations on the computer."
        ::= { ntsystem 5 }

    ntsystemFileControlBytesPerSec OBJECT-TYPE
        SYNTAX INTEGER
        ACCESS read-only
        STATUS mandatory
        DESCRIPTION
            "File Control Bytes/sec is an aggregate of bytes transferred for all file system operations that are neither reads nor writes.  These operations usually include file system control requests or requests for information about device characteristics or status."
        ::= { ntsystem 6 }

    ntsystemContextSwitchesPerSec OBJECT-TYPE
        SYNTAX Counter
        ACCESS read-only
        STATUS mandatory
        DESCRIPTION
            "Context Switches/sec is the rate of switches from one thread to another.  Thread switches can occur either inside of a single process or across processes.  A thread switch may be caused either by one thread asking another for information, or by a thread being preempted by another, higher priority thread becoming ready to run.  Unlike some early operating systems, Windows NT uses process boundaries for subsystem protection in addition to the traditional protection of User and Privileged modes.  These subsystem processes provide additional protection.  Therefore, some work done by Windows NT on behalf of an application may appear in other subsystem processes in addition to the Privileged Time in the application.  Switching to the subsystem process causes one Context Switch in the application thread.  Switching back causes another Context Switch in the subsystem thread."
        ::= { ntsystem 7 }

    ntsystemSystemCallsPerSec OBJECT-TYPE
        SYNTAX Counter
        ACCESS read-only
        STATUS mandatory
        DESCRIPTION
            "Systems Calls/sec is the frequency of calls to Windows NT system service routines.  These routines perform all of the basic scheduling and synchronization of activities on the computer, and provide access to non-graphical devices, memory management, and name space management."
        ::= { ntsystem 8 }

    ntsystemPercentTotalProcessorTime OBJECT-TYPE
        SYNTAX INTEGER
        ACCESS read-only
        STATUS mandatory
        DESCRIPTION
            "The % Total Processor Time is the average percentage of time that all the processors on the system are busy executing non-idle threads.  On a multi-processor system, if all processors are always busy this is 100%, if all processors are 50% busy this is 50% and if 1/4th of the processors are 100% busy this is 25%.  It can be viewed as the fraction of the time spent doing useful work.  Each processor is assigned an Idle thread in the Idle process which consumes those unproductive processor cycles not used by any other threads.  "
        ::= { ntsystem 9 }

    ntsystemPercentTotalUserTime OBJECT-TYPE
        SYNTAX INTEGER
        ACCESS read-only
        STATUS mandatory
        DESCRIPTION
            "The % Total User Time is the average percentage of time spent in User mode by all processors.  On a multi-processor system, if all processors are always in User mode this is 100%, if all processors are 50% in User mode this is 50% and if 1/4th of the processors are in User mode this is 25%.  Applications execute in User Mode, as do subsystems like the window manager and the graphics engine.  Code executing in User Mode cannot damage the integrity of the Windows NT Executive, Kernel, and device drivers.  Unlike some early operating systems, Windows NT uses process boundaries for subsystem protection in addition to the traditional protection of User and Privileged modes.  These subsystem processes provide additional protection.  Therefore, some work done by Windows NT on behalf of an application may appear in other subsystem processes in addition to the Privileged Time in the application process."
        ::= { ntsystem 10 }

    ntsystemPercentTotalPrivilegedTime OBJECT-TYPE
        SYNTAX INTEGER
        ACCESS read-only
        STATUS mandatory
        DESCRIPTION
            "The % Total Privileged Time is the average percentage of time spent in Privileged mode by all processors.  On a multi-processor system, if all processors are always in Privileged mode this is 100%, and if 1/4th of the processors are in Privileged mode this is 25%.  When a Windows NT system service is called, the service will often run in Privileged Mode in order to gain access to system-private data.  Such data is protected from access by threads executing in User Mode.  Calls to the system may be explicit, or they may be implicit such as when a page fault or an interrupt occurs.  Unlike some early operating systems, Windows NT uses process boundaries for subsystem protection in addition to the traditional protection of User and Privileged modes.  These subsystem processes provide additional protection.  Therefore, some work done by Windows NT on behalf of an application may appear in other subsystem processes in addition to the Privileged Time in the application process."
        ::= { ntsystem 11 }

    ntsystemTotalInterruptsPerSec OBJECT-TYPE
        SYNTAX Counter
        ACCESS read-only
        STATUS mandatory
        DESCRIPTION
            "Total Interrupts/sec is the rate the computer is receiving and servicing hardware interrupts.  Some devices that may generate interrupts are the system timer, the mouse, data communication lines, network interface cards and other peripheral devices.  This counter provides an indication of how busy these devices are on a computer-wide basis.  See also Processor:Interrupts/sec."
        ::= { ntsystem 12 }

    ntsystemFileDataOperationsPerSec OBJECT-TYPE
        SYNTAX Counter
        ACCESS read-only
        STATUS mandatory
        DESCRIPTION
            "File Data Operations per second is the rate that the computer is issuing Read and Write operations to file system devices.  It does not include File Control Operations."
        ::= { ntsystem 13 }

    ntsystemSystemUpTime OBJECT-TYPE
        SYNTAX TimeTicks
        ACCESS read-only
        STATUS mandatory
        DESCRIPTION
            "Total Time (in seconds) that the computer has been operational since it was last started."
        ::= { ntsystem 14 }

    ntsystemProcessorQueueLength OBJECT-TYPE
        SYNTAX INTEGER
        ACCESS read-only
        STATUS mandatory
        DESCRIPTION
            "Processor Queue Length is the instantaneous length of the processor queue in units of threads.  This counter is always 0 unless you are also monitoring a thread counter.  All processors use a single queue in which threads wait for processor cycles.  This length does not include the threads that are currently executing.  A sustained processor queue length greater than two generally indicates processor congestion.  This is an instantaneous count, not an average over the time interval."
        ::= { ntsystem 15 }

    ntsystemAlignmentFixupsPerSec OBJECT-TYPE
        SYNTAX Counter
        ACCESS read-only
        STATUS mandatory
        DESCRIPTION
            "Alignment Fixups/sec is the rate of alignment faults fixed by the system."
        ::= { ntsystem 16 }

    ntsystemExceptionDispatchesPerSec OBJECT-TYPE
        SYNTAX Counter
        ACCESS read-only
        STATUS mandatory
        DESCRIPTION
            "Exception Dispatches/sec is the rate of exceptions dispatched by the system."
        ::= { ntsystem 17 }

    ntsystemFloatingEmulationsPerSec OBJECT-TYPE
        SYNTAX Counter
        ACCESS read-only
        STATUS mandatory
        DESCRIPTION
            "Floating Emulations/sec is the rate of floating emulations performed by the system."
        ::= { ntsystem 18 }

    ntsystemPercentTotalDPCTime OBJECT-TYPE
        SYNTAX INTEGER
        ACCESS read-only
        STATUS mandatory
        DESCRIPTION
            "% Total DPC Time is the sum of % DPC Time of all processors divided by the number of processors in the system.  (See Processor: % DPC Time for detail.)"
        ::= { ntsystem 19 }

    ntsystemPercentTotalInterruptTime OBJECT-TYPE
        SYNTAX INTEGER
        ACCESS read-only
        STATUS mandatory
        DESCRIPTION
            "% Total Interrupt Time is the sum of % Interrupt Time of all processors divided by the number of processors in the system.  (See Processor: % Interrupt Time for detail.)"
        ::= { ntsystem 20 }

    ntsystemTotalDPCsQueuedPerSec OBJECT-TYPE
        SYNTAX Counter
        ACCESS read-only
        STATUS mandatory
        DESCRIPTION
            "Total DPCs Queued/sec is the rate DPC objects are queued to all processors' DPC queues."
        ::= { ntsystem 21 }

    ntsystemTotalDPCRate OBJECT-TYPE
        SYNTAX INTEGER
        ACCESS read-only
        STATUS mandatory
        DESCRIPTION
            "Total DPC Rate is the average rate DPC objects are queued to all processors' DPC queue per clock tick."
        ::= { ntsystem 22 }

    ntsystemTotalDPCBypassesPerSec OBJECT-TYPE
        SYNTAX Counter
        ACCESS read-only
        STATUS mandatory
        DESCRIPTION
            "Total DPC Bypasses/sec is the overall rate Dispatch interrupts were short-circuited across all processors."
        ::= { ntsystem 23 }

    ntsystemTotalAPCBypassesPerSec OBJECT-TYPE
        SYNTAX Counter
        ACCESS read-only
        STATUS mandatory
        DESCRIPTION
            "Total APC Bypasses/sec is the overall rate kernel APC interrupts were short-circuited across all processors."
        ::= { ntsystem 24 }

    ntsystemPercentRegistryQuotaInUse OBJECT-TYPE
        SYNTAX INTEGER
        ACCESS read-only
        STATUS mandatory
        DESCRIPTION
            "% Registry Quota In Use indicates the percentage of the Total Registry Quota Allowed currently in use by the system."
        ::= { ntsystem 25 }

    -- packet Filtering MIB

    packet-Filtering OBJECT IDENTIFIER ::= { performance 34 }

    packetfilterTotalDroppedFrames OBJECT-TYPE
        SYNTAX Counter
        ACCESS read-only
        STATUS mandatory
        DESCRIPTION
            "The total number of dropped or filtered frames."
        ::= { packet-Filtering 1 }

    packetfilterFramesDroppedDueToFilterDenial OBJECT-TYPE
        SYNTAX Counter
        ACCESS read-only
        STATUS mandatory
        DESCRIPTION
            "Total number of frames dropped because dynamic packet filtering did not allow the data."
        ::= { packet-Filtering 2 }

    packetfilterFramesDroppedDueToProtocolViolations OBJECT-TYPE
        SYNTAX Counter
        ACCESS read-only
        STATUS mandatory
        DESCRIPTION
            "This is the total of the number of frames dropped because of some protocol irregularity."
        ::= { packet-Filtering 3 }

    packetfilterTotalIncomingConnections OBJECT-TYPE
        SYNTAX Counter
        ACCESS read-only
        STATUS mandatory
        DESCRIPTION
            "This is the total of the number of connections made through the filtered interfaces."
        ::= { packet-Filtering 4 }

    packetfilterTotalLostLoggingFrames OBJECT-TYPE
        SYNTAX Counter
        ACCESS read-only
        STATUS mandatory
        DESCRIPTION
            "This is the total of the number of frames dropped that could not be logged."
        ::= { packet-Filtering 5 }

    -- web Service MIB

    webserviceweb-ServiceTable OBJECT-TYPE
        SYNTAX SEQUENCE OF webserviceweb-ServiceEntry
        ACCESS not-accessible
        STATUS mandatory
        DESCRIPTION
            "A table containing performance information for instances of 'web-Service' objects."
        ::= { performance 35 }

    webserviceweb-ServiceEntry OBJECT-TYPE
        SYNTAX webserviceweb-ServiceEntry
        ACCESS not-accessible
        STATUS mandatory
        DESCRIPTION
            "Performance information for one particular instance of 'web-Service' object."
        INDEX { webserviceweb-ServiceIndex }
        ::= { webserviceweb-ServiceTable 1 }

    webserviceweb-ServiceEntry ::=
        SEQUENCE {
            webserviceweb-ServiceIndex INTEGER,
            webserviceweb-ServiceInstance DisplayString,
            webserviceBytesSentPerSec INTEGER,
            webserviceBytesReceivedPerSec INTEGER,
            webserviceBytesTotalPerSec INTEGER,
            webserviceTotalFilesSent INTEGER,
            webserviceFilesSentPerSec Counter,
            webserviceTotalFilesReceived INTEGER,
            webserviceFilesReceivedPerSec Counter,
            webserviceTotalFilesTransferred INTEGER,
            webserviceFilesPerSec Counter,
            webserviceCurrentAnonymousUsers INTEGER,
            webserviceCurrentNonAnonymousUsers INTEGER,
            webserviceTotalAnonymousUsers INTEGER,
            webserviceAnonymousUsersPerSec Counter,
            webserviceTotalNonAnonymousUsers INTEGER,
            webserviceNonAnonymousUsersPerSec Counter,
            webserviceMaximumAnonymousUsers INTEGER,
            webserviceMaximumNonAnonymousUsers INTEGER,
            webserviceCurrentConnections INTEGER,
            webserviceMaximumConnections INTEGER,
            webserviceTotalConnectionAttempts INTEGER,
            webserviceConnectionAttemptsPerSec Counter,
            webserviceTotalLogonAttempts INTEGER,
            webserviceLogonAttemptsPerSec Counter,
            webserviceTotalGetRequests INTEGER,
            webserviceGetRequestsPerSec Counter,
            webserviceTotalPostRequests INTEGER,
            webservicePostRequestsPerSec Counter,
            webserviceTotalHeadRequests INTEGER,
            webserviceHeadRequestsPerSec Counter,
            webserviceTotalPutRequests INTEGER,
            webservicePutRequestsPerSec Counter,
            webserviceTotalDeleteRequests INTEGER,
            webserviceDeleteRequestsPerSec Counter,
            webserviceTotalTraceRequests INTEGER,
            webserviceSystemCodeResidentBytes Counter,
            webserviceTotalOtherRequestMethods INTEGER,
            webserviceOtherRequestMethodsPerSec Counter,
            webserviceTotalMethodRequests INTEGER,
            webserviceTotalMethodRequestsPerSec Counter,
            webserviceTotalCGIRequests INTEGER,
            webserviceCGIRequestsPerSec Counter,
            webserviceTotalISAPIExtensionRequests INTEGER,
            webserviceISAPIExtensionRequestsPerSec Counter,
            webserviceTotalNotFoundErrors INTEGER,
            webserviceNotFoundErrorsPerSec Counter,
            webserviceCurrentCGIRequests INTEGER,
            webserviceCurrentISAPIExtensionRequests INTEGER,
            webserviceMaximumCGIRequests INTEGER,
            webserviceMaximumISAPIExtensionRequests INTEGER,
            webserviceTotalBlockedAsyncIPerORequests INTEGER,
            webserviceTotalAllowedAsyncIPerORequests INTEGER,
            webserviceTotalRejectedAsyncIPerORequests INTEGER,
            webserviceCurrentBlockedAsyncIPerORequests INTEGER,
            webserviceMeasuredAsyncIPerOBandwidthUsage INTEGER
        }

    webserviceweb-ServiceIndex OBJECT-TYPE
        SYNTAX INTEGER
        ACCESS read-only
        STATUS mandatory
        DESCRIPTION
            "Index."
        ::= { webserviceweb-ServiceEntry 1 }

    webserviceweb-ServiceInstance OBJECT-TYPE
        SYNTAX DisplayString
        ACCESS read-only
        STATUS mandatory
        DESCRIPTION
            "Instance name."
        ::= { webserviceweb-ServiceEntry 2 }

    webserviceBytesSentPerSec OBJECT-TYPE
        SYNTAX INTEGER
        ACCESS read-only
        STATUS mandatory
        DESCRIPTION
            "Bytes Sent/sec is the rate that data bytes are sent by the Web service."
        ::= { webserviceweb-ServiceEntry 3 }

    webserviceBytesReceivedPerSec OBJECT-TYPE
        SYNTAX INTEGER
        ACCESS read-only
        STATUS mandatory
        DESCRIPTION
            "Bytes Received/sec is the rate that data bytes are received by the Web service."
        ::= { webserviceweb-ServiceEntry 4 }

    webserviceBytesTotalPerSec OBJECT-TYPE
        SYNTAX INTEGER
        ACCESS read-only
        STATUS mandatory
        DESCRIPTION
            "Bytes Total/sec is the sum of Bytes Sent/sec and Bytes Received/sec.  This is the total rate of bytes transferred by the Web service."
        ::= { webserviceweb-ServiceEntry 5 }

    webserviceTotalFilesSent OBJECT-TYPE
        SYNTAX INTEGER
        ACCESS read-only
        STATUS mandatory
        DESCRIPTION
            "Total Files Sent is the total number of files sent by the Web service (counted since service startup)."
        ::= { webserviceweb-ServiceEntry 6 }

    webserviceFilesSentPerSec OBJECT-TYPE
        SYNTAX Counter
        ACCESS read-only
        STATUS mandatory
        DESCRIPTION
            "The rate files are sent by the Web service."
        ::= { webserviceweb-ServiceEntry 7 }

    webserviceTotalFilesReceived OBJECT-TYPE
        SYNTAX INTEGER
        ACCESS read-only
        STATUS mandatory
        DESCRIPTION
            "Total Files Received is the total number of files received by the Web service (counted since service startup)."
        ::= { webserviceweb-ServiceEntry 8 }

    webserviceFilesReceivedPerSec OBJECT-TYPE
        SYNTAX Counter
        ACCESS read-only
        STATUS mandatory
        DESCRIPTION
            "The rate files are received by the Web service."
        ::= { webserviceweb-ServiceEntry 9 }

    webserviceTotalFilesTransferred OBJECT-TYPE
        SYNTAX INTEGER
        ACCESS read-only
        STATUS mandatory
        DESCRIPTION
            "Total Files Transferred is the sum of Files Sent and Files Received.  This is the total number of files transferred by the Web service (counted since service startup)."
        ::= { webserviceweb-ServiceEntry 10 }

    webserviceFilesPerSec OBJECT-TYPE
        SYNTAX Counter
        ACCESS read-only
        STATUS mandatory
        DESCRIPTION
            "The rate files are transferred, that is, sent and received by the Web service."
        ::= { webserviceweb-ServiceEntry 11 }

    webserviceCurrentAnonymousUsers OBJECT-TYPE
        SYNTAX INTEGER
        ACCESS read-only
        STATUS mandatory
        DESCRIPTION
            "Current Anonymous Users is the number of users who currently have an anonymous connection using the Web service."
        ::= { webserviceweb-ServiceEntry 12 }

    webserviceCurrentNonAnonymousUsers OBJECT-TYPE
        SYNTAX INTEGER
        ACCESS read-only
        STATUS mandatory
        DESCRIPTION
            "Current NonAnonymous Users is the number of users who currently have a non-anonymous connection using the Web service."
        ::= { webserviceweb-ServiceEntry 13 }

    webserviceTotalAnonymousUsers OBJECT-TYPE
        SYNTAX INTEGER
        ACCESS read-only
        STATUS mandatory
        DESCRIPTION
            "Total Anonymous Users is the total number of users who established an anonymous connection with the Web service (counted since service startup)."
        ::= { webserviceweb-ServiceEntry 14 }

    webserviceAnonymousUsersPerSec OBJECT-TYPE
        SYNTAX Counter
        ACCESS read-only
        STATUS mandatory
        DESCRIPTION
            "The rate users are making anonymous connections using the Web service."
        ::= { webserviceweb-ServiceEntry 15 }

    webserviceTotalNonAnonymousUsers OBJECT-TYPE
        SYNTAX INTEGER
        ACCESS read-only
        STATUS mandatory
        DESCRIPTION
            "Total NonAnonymous Users is the total number of users who established a non-anonymous connection with the Web service (counted since service startup)."
        ::= { webserviceweb-ServiceEntry 16 }

    webserviceNonAnonymousUsersPerSec OBJECT-TYPE
        SYNTAX Counter
        ACCESS read-only
        STATUS mandatory
        DESCRIPTION
            "The rate users are making non-anonymous connections using the Web service."
        ::= { webserviceweb-ServiceEntry 17 }

    webserviceMaximumAnonymousUsers OBJECT-TYPE
        SYNTAX INTEGER
        ACCESS read-only
        STATUS mandatory
        DESCRIPTION
            "Maximum Anonymous Users is the maximum number of users who established concurrent anonymous connections using the Web service (counted since service startup)."
        ::= { webserviceweb-ServiceEntry 18 }

    webserviceMaximumNonAnonymousUsers OBJECT-TYPE
        SYNTAX INTEGER
        ACCESS read-only
        STATUS mandatory
        DESCRIPTION
            "Maximum NonAnonymous Users is the maximum number of users who established concurrent non-anonymous connections using the Web service (counted since service startup)."
        ::= { webserviceweb-ServiceEntry 19 }

    webserviceCurrentConnections OBJECT-TYPE
        SYNTAX INTEGER
        ACCESS read-only
        STATUS mandatory
        DESCRIPTION
            "Current Connections is the current number of connections established with the Web service."
        ::= { webserviceweb-ServiceEntry 20 }

    webserviceMaximumConnections OBJECT-TYPE
        SYNTAX INTEGER
        ACCESS read-only
        STATUS mandatory
        DESCRIPTION
            "Maximum Connections is the maximum number of simultaneous connections established with the Web service."
        ::= { webserviceweb-ServiceEntry 21 }

    webserviceTotalConnectionAttempts OBJECT-TYPE
        SYNTAX INTEGER
        ACCESS read-only
        STATUS mandatory
        DESCRIPTION
            "Total Connection Attempts is the number of connections that have been attempted using the Web service (counted since service startup)."
        ::= { webserviceweb-ServiceEntry 22 }

    webserviceConnectionAttemptsPerSec OBJECT-TYPE
        SYNTAX Counter
        ACCESS read-only
        STATUS mandatory
        DESCRIPTION
            "The rate that connections using the Web service are being attempted."
        ::= { webserviceweb-ServiceEntry 23 }

    webserviceTotalLogonAttempts OBJECT-TYPE
        SYNTAX INTEGER
        ACCESS read-only
        STATUS mandatory
        DESCRIPTION
            "Total Logon Attempts is the number of logons that have been attempted using the Web service (counted since service startup)."
        ::= { webserviceweb-ServiceEntry 24 }

    webserviceLogonAttemptsPerSec OBJECT-TYPE
        SYNTAX Counter
        ACCESS read-only
        STATUS mandatory
        DESCRIPTION
            "The rate that logons using the Web service are being attempted."
        ::= { webserviceweb-ServiceEntry 25 }

    webserviceTotalGetRequests OBJECT-TYPE
        SYNTAX INTEGER
        ACCESS read-only
        STATUS mandatory
        DESCRIPTION
            "Total Get Requests is the number of HTTP requests using the GET method (counted since service startup).  Get requests are generally used for basic file retrievals or image maps, though they can be used with forms."
        ::= { webserviceweb-ServiceEntry 26 }

    webserviceGetRequestsPerSec OBJECT-TYPE
        SYNTAX Counter
        ACCESS read-only
        STATUS mandatory
        DESCRIPTION
            "The rate HTTP requests using the GET method are made.  Get requests are generally used for basic file retrievals or image maps, though they can be used with forms."
        ::= { webserviceweb-ServiceEntry 27 }

    webserviceTotalPostRequests OBJECT-TYPE
        SYNTAX INTEGER
        ACCESS read-only
        STATUS mandatory
        DESCRIPTION
            "Total Post Requests is the number of HTTP requests using the POST method (counted since service startup).  Post requests are generally used for forms or gateway requests."
        ::= { webserviceweb-ServiceEntry 28 }

    webservicePostRequestsPerSec OBJECT-TYPE
        SYNTAX Counter
        ACCESS read-only
        STATUS mandatory
        DESCRIPTION
            "The rate HTTP requests using the POST method are made.  Post requests are generally used for forms or gateway requests."
        ::= { webserviceweb-ServiceEntry 29 }

    webserviceTotalHeadRequests OBJECT-TYPE
        SYNTAX INTEGER
        ACCESS read-only
        STATUS mandatory
        DESCRIPTION
            "Total Head Requests is the number of HTTP requests using the HEAD method (counted since service startup).  Head requests generally indicate a client is querying the state of a document they already have to see if it needs to be refreshed."
        ::= { webserviceweb-ServiceEntry 30 }

    webserviceHeadRequestsPerSec OBJECT-TYPE
        SYNTAX Counter
        ACCESS read-only
        STATUS mandatory
        DESCRIPTION
            "The rate HTTP requests using the HEAD method are made.  Head requests generally indicate a client is querying the state of a document they already have to see if it needs to be refreshed."
        ::= { webserviceweb-ServiceEntry 31 }

    webserviceTotalPutRequests OBJECT-TYPE
        SYNTAX INTEGER
        ACCESS read-only
        STATUS mandatory
        DESCRIPTION
            "Total Put Requests is the number of HTTP requests using the PUT method (counted since service startup)."
        ::= { webserviceweb-ServiceEntry 32 }

    webservicePutRequestsPerSec OBJECT-TYPE
        SYNTAX Counter
        ACCESS read-only
        STATUS mandatory
        DESCRIPTION
            "The rate HTTP requests using the PUT method are made."
        ::= { webserviceweb-ServiceEntry 33 }

    webserviceTotalDeleteRequests OBJECT-TYPE
        SYNTAX INTEGER
        ACCESS read-only
        STATUS mandatory
        DESCRIPTION
            "Total Delete Requests is the number of HTTP requests using the DELETE method (counted since service startup).  Delete requests are generally used for file removals."
        ::= { webserviceweb-ServiceEntry 34 }

    webserviceDeleteRequestsPerSec OBJECT-TYPE
        SYNTAX Counter
        ACCESS read-only
        STATUS mandatory
        DESCRIPTION
            "The rate HTTP requests using the DELETE method are made.  Delete requests are generally used for file removals."
        ::= { webserviceweb-ServiceEntry 35 }

    webserviceTotalTraceRequests OBJECT-TYPE
        SYNTAX INTEGER
        ACCESS read-only
        STATUS mandatory
        DESCRIPTION
            "Total Trace Requests is the number of HTTP requests using the TRACE method (counted since service startup).  Trace requests allow the client to see what is being received at the end of the request chain and use the information for diagnostic purposes."
        ::= { webserviceweb-ServiceEntry 36 }

    webserviceSystemCodeResidentBytes OBJECT-TYPE
        SYNTAX Counter
        ACCESS read-only
        STATUS mandatory
        DESCRIPTION
            "System Code Resident Bytes"
        ::= { webserviceweb-ServiceEntry 37 }

    webserviceTotalOtherRequestMethods OBJECT-TYPE
        SYNTAX INTEGER
        ACCESS read-only
        STATUS mandatory
        DESCRIPTION
            "Total Other Request Methods is the number of HTTP requests that are not GET, POST, PUT, DELETE, TRACE or HEAD methods (counted since service startup).  These may include LINK or other methods supported by gateway applications."
        ::= { webserviceweb-ServiceEntry 38 }

    webserviceOtherRequestMethodsPerSec OBJECT-TYPE
        SYNTAX Counter
        ACCESS read-only
        STATUS mandatory
        DESCRIPTION
            "The rate HTTP requests are made that do not use the GET, POST, PUT, DELETE, TRACE or HEAD methods.  These may include LINK or other methods supported by gateway applications."
        ::= { webserviceweb-ServiceEntry 39 }

    webserviceTotalMethodRequests OBJECT-TYPE
        SYNTAX INTEGER
        ACCESS read-only
        STATUS mandatory
        DESCRIPTION
            "Total Method Requests is the number of HTTP GET, POST, PUT, DELETE, TRACE, HEAD and other method requests (counted since service startup)."
        ::= { webserviceweb-ServiceEntry 40 }

    webserviceTotalMethodRequestsPerSec OBJECT-TYPE
        SYNTAX Counter
        ACCESS read-only
        STATUS mandatory
        DESCRIPTION
            "The rate HTTP requests using GET, POST, PUT, DELETE, TRACE or HEAD methods are made."
        ::= { webserviceweb-ServiceEntry 41 }

    webserviceTotalCGIRequests OBJECT-TYPE
        SYNTAX INTEGER
        ACCESS read-only
        STATUS mandatory
        DESCRIPTION
            "Total Common Gateway Interface (CGI) requests are custom gateway executables (.exe) the administrator can install to add forms processing or other dynamic data sources.  CGI requests spawn a process on the server which can be a large drain on server resources.  The count is the total since service startup."
        ::= { webserviceweb-ServiceEntry 42 }

    webserviceCGIRequestsPerSec OBJECT-TYPE
        SYNTAX Counter
        ACCESS read-only
        STATUS mandatory
        DESCRIPTION
            "The rate of CGI requests that are simultaneously being processed by the Web service."
        ::= { webserviceweb-ServiceEntry 43 }

    webserviceTotalISAPIExtensionRequests OBJECT-TYPE
        SYNTAX INTEGER
        ACCESS read-only
        STATUS mandatory
        DESCRIPTION
            "Total ISAPI Extension Requests are custom gateway Dynamic Link Libraries (.dll) the administrator can install to add forms processing or other dynamic data sources.  Unlike CGI requests, ISAPI requests are simple calls to a DLL library routine, thus they are better suited to high performance gateway applications.  The count is the total since service startup."
        ::= { webserviceweb-ServiceEntry 44 }

    webserviceISAPIExtensionRequestsPerSec OBJECT-TYPE
        SYNTAX Counter
        ACCESS read-only
        STATUS mandatory
        DESCRIPTION
            "The rate of ISAPI Extension requests that are simultaneously being processed by the Web service."
        ::= { webserviceweb-ServiceEntry 45 }

    webserviceTotalNotFoundErrors OBJECT-TYPE
        SYNTAX INTEGER
        ACCESS read-only
        STATUS mandatory
        DESCRIPTION
            "Total Not Found Errors is the number of requests that couldn't be satisfied by the server because the requested document could not be found.  These are generally reported as an HTTP 404 error code to the client.  The count is the total since service startup."
        ::= { webserviceweb-ServiceEntry 46 }

    webserviceNotFoundErrorsPerSec OBJECT-TYPE
        SYNTAX Counter
        ACCESS read-only
        STATUS mandatory
        DESCRIPTION
            "The rate of errors due to requests that couldn't be satisfied by the server because the requested document could not be found.  These are generally reported as an HTTP 404 error code to the client."
        ::= { webserviceweb-ServiceEntry 47 }

    webserviceCurrentCGIRequests OBJECT-TYPE
        SYNTAX INTEGER
        ACCESS read-only
        STATUS mandatory
        DESCRIPTION
            "Current CGI Requests is the current number of CGI requests that are simultaneously being processed by the Web service."
        ::= { webserviceweb-ServiceEntry 48 }

    webserviceCurrentISAPIExtensionRequests OBJECT-TYPE
        SYNTAX INTEGER
        ACCESS read-only
        STATUS mandatory
        DESCRIPTION
            "Current ISAPI Extension Requests is the current number of Extension requests that are simultaneously being processed by the Web service."
        ::= { webserviceweb-ServiceEntry 49 }

    webserviceMaximumCGIRequests OBJECT-TYPE
        SYNTAX INTEGER
        ACCESS read-only
        STATUS mandatory
        DESCRIPTION
            "Maximum CGI Requests is the maximum number of CGI requests simultaneously processed by the Web service."
        ::= { webserviceweb-ServiceEntry 50 }

    webserviceMaximumISAPIExtensionRequests OBJECT-TYPE
        SYNTAX INTEGER
        ACCESS read-only
        STATUS mandatory
        DESCRIPTION
            "Maximum ISAPI Extension Requests is the maximum number of Extension requests simultaneously processed by the Web service."
        ::= { webserviceweb-ServiceEntry 51 }

    webserviceTotalBlockedAsyncIPerORequests OBJECT-TYPE
        SYNTAX INTEGER
        ACCESS read-only
        STATUS mandatory
        DESCRIPTION
            "Total requests temporarily blocked due to bandwidth throttling settings (counted since service startup)."
        ::= { webserviceweb-ServiceEntry 52 }

    webserviceTotalAllowedAsyncIPerORequests OBJECT-TYPE
        SYNTAX INTEGER
        ACCESS read-only
        STATUS mandatory
        DESCRIPTION
            "Total requests allowed by bandwidth throttling settings (counted since service startup)."
        ::= { webserviceweb-ServiceEntry 53 }

    webserviceTotalRejectedAsyncIPerORequests OBJECT-TYPE
        SYNTAX INTEGER
        ACCESS read-only
        STATUS mandatory
        DESCRIPTION
            "Total requests rejected due to bandwidth throttling settings (counted since service startup)."
        ::= { webserviceweb-ServiceEntry 54 }

    webserviceCurrentBlockedAsyncIPerORequests OBJECT-TYPE
        SYNTAX INTEGER
        ACCESS read-only
        STATUS mandatory
        DESCRIPTION
            "Current requests temporarily blocked due to bandwidth throttling settings."
        ::= { webserviceweb-ServiceEntry 55 }

    webserviceMeasuredAsyncIPerOBandwidthUsage OBJECT-TYPE
        SYNTAX INTEGER
        ACCESS read-only
        STATUS mandatory
        DESCRIPTION
            "Measured bandwidth of asynchronous I/O averaged over a minute."
        ::= { webserviceweb-ServiceEntry 56 }

    END
